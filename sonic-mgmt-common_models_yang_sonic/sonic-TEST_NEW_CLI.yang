module sonic-TEST_NEW_CLI {
	namespace "http://github.com/Azure/sonic-TEST_NEW_CLI";
	prefix sonic-TEST_NEW_CLI;

	import ietf-inet-types {
		prefix inet;
	}

	organization
		"SONiC";

	contact
		"SONiC";

	description
		"SONIC TEST_NEW_CLI";

	revision 2026-07-02 {
		description
			"Initial revision.";
	}

	container sonic-TEST_NEW_CLI {
		container TEST_NEW_CLI {
			container test {
				leaf IP_PREFIX {
					type inet:ipv4-prefix; //A.B.C.D/M
				}
				leaf with {
					type enumeration {
						enum with;
					}
				}
				leaf IFNAME {
					type string; // IFNAME
				}
			}
		}
	}
}
