module sonic-frr-SR_TRAFFIC_ENG_NODE {
    namespace "http://github.com/sonic-net/frr/sonic-frr-SR_TRAFFIC_ENG_NODE";
    prefix frr-SR_TRAFFIC_ENG_NODE;
    yang-version 1.1;

    import ietf-inet-types {
        prefix inet;
    }

    organization
        "SONiC";

    contact
        "SONiC";

    description
        "SONIC frr-SR_TRAFFIC_ENG_NODE FRR YANG";

    revision 2024-12-23 {
        description
            "Initial revision.";
    }
    container sonic-frr-SR_TRAFFIC_ENG_NODE {
        container SR_TRAFFIC_ENG_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf segment-list {
                    type enumeration {
                        enum segment-list;
                    }
                }                  //segment-list
                leaf SEGMENT_LIST_NAME {
                    type string;
                }                  //WORD
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list SEGMENT-LIST {
                key "PREFIX";
                leaf PREFIX {
                    type string; 
                } 
                leaf SEGMENT_LIST_NAME {
                    type string;
                }                  //WORD
            }
            list QUIT {
                key "PREFIX";
                leaf PREFIX {
                    type string; 
                } 
            }
            list POLICY {
                key "PREFIX";
                leaf PREFIX {
                    type string; 
                } 
                leaf color {
                    type enumeration {
                        enum color;
                    }
                }                  //color
                leaf SR_POLICY_COLOR_VALUE {
                    type int32;
                }                  //(0-4294967295)
                leaf endpoint {
                    type enumeration {
                        enum endpoint;
                    }
                }                  //endpoint
                leaf ENDPOINT_IP_ADDRESS {
                    type union {
                        type inet:ipv4-address;
                        type inet:ipv6-address;
                    }
                }                  //<A.B.C.D|X:X::X:X> ['SR Policy endpoint IPv4 address', 'SR Policy endpoint IPv6 address']
            }
            list PCEP {
                key "PREFIX";
                leaf PREFIX {
                    type string; 
                } 
            }
            list MPLS-TE {
                key "PREFIX";
                leaf PREFIX {
                    type string; 
                } 
                leaf on {
                    type enumeration {
                        enum on;
                    }
                }                  //on
                leaf import {
                    type enumeration {
                        enum import;
                    }
                }                  //import
                leaf IMPORT_CHOICE_CASE {
                    type enumeration {
                        enum ospfv2;
                        enum ospfv3;
                        enum isis;
                    }
                }                  //<ospfv2|ospfv3|isis> ['Origin ospfv2', 'Origin ospfv3', 'Origin isis']
            }
            list EXIT {
                key "PREFIX";
                leaf PREFIX {
                    type string; 
                } 
            }
            list END {
                key "PREFIX";
                leaf PREFIX {
                    type string; 
                } 
            }
            list NO_POLICY {
                key "PREFIX";
                leaf PREFIX {
                    type string; 
                } 
                leaf color {
                    type enumeration {
                        enum color;
                    }
                }                  //color
                leaf SR_POLICY_COLOR_VALUE {
                    type int32;
                }                  //(0-4294967295)
                leaf endpoint {
                    type enumeration {
                        enum endpoint;
                    }
                }                  //endpoint
                leaf ENDPOINT_IP_ADDRESS {
                    type union {
                        type inet:ipv4-address;
                        type inet:ipv6-address;
                    }
                }                  //<A.B.C.D|X:X::X:X> ['SR Policy endpoint IPv4 address', 'SR Policy endpoint IPv6 address']
            }
            list NO_MPLS-TE {
                key "PREFIX";
                leaf PREFIX {
                    type string; 
                } 
                leaf import {
                    type enumeration {
                        enum import;
                    }
                }                  //import
                leaf on {
                    type enumeration {
                        enum on;
                    }
                }                  //on
            }
            list NO_OUTPUT_FILE {
                key "PREFIX";
                leaf PREFIX {
                    type string; 
                } 
                leaf PATH_TO_DUMP_OUTPUT {
                    type string;
                }                  //FILE
            }
        }

    }
}
