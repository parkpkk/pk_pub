module sonic-frr-VIEW_NODE {
    namespace "http://github.com/sonic-net/frr/sonic-frr-VIEW_NODE";
    prefix frr-VIEW_NODE;
    yang-version 1.1;

    import ietf-inet-types {
        prefix inet;
    }

    organization
        "SONiC";

    contact
        "SONiC";

    description
        "SONIC frr-VIEW_NODE FRR YANG";

    revision 2024-12-23 {
        description
            "Initial revision.";
    }
    container sonic-frr-VIEW_NODE {

    }
}
