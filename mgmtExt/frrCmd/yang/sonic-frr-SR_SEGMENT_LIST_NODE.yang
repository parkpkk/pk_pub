module sonic-frr-SR_SEGMENT_LIST_NODE {
    namespace "http://github.com/sonic-net/frr/sonic-frr-SR_SEGMENT_LIST_NODE";
    prefix frr-SR_SEGMENT_LIST_NODE;
    yang-version 1.1;

    import ietf-inet-types {
        prefix inet;
    }

    organization
        "SONiC";

    contact
        "SONiC";

    description
        "SONIC frr-SR_SEGMENT_LIST_NODE FRR YANG";

    revision 2024-12-23 {
        description
            "Initial revision.";
    }
    container sonic-frr-SR_SEGMENT_LIST_NODE {
        container SR_SEGMENT_LIST_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf index {
                    type enumeration {
                        enum index;
                    }
                }                  //index
                leaf INDEX_VALUE {
                    type int32;
                }                  //(0-4294967295)
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list QUIT {
                key "PREFIX";
                leaf PREFIX {
                    type string; 
                } 
            }
            list INDEX {
                key "PREFIX";
                leaf PREFIX {
                    type string; 
                } 
                leaf INDEX_VALUE {
                    type int32;
                }                  //(0-4294967295)
                leaf mpls_label {
                    type enumeration {
                        enum mpls_label;
                    }
                }                  //label
                leaf LABEL_VALUE {
                    type int32;
                }                  //(16-1048575)
                leaf nai {
                    type enumeration {
                        enum nai;
                    }
                }                  //nai
                leaf nai_prefix {
                    type enumeration {
                        enum nai_prefix;
                    }
                }                  //prefix
                leaf PREFIX_IP_PREFIX {
                    type union {
                        type inet:ipv4-prefix;
                        type inet:ipv6-prefix;
                    }
                }                  //<A.B.C.D/M|X:X::X:X/M> ['NAI IPv4 prefix identifier', 'NAI IPv6 prefix identifier']
                leaf algorithm {
                    type enumeration {
                        enum algorithm;
                    }
                }                  //algorithm
                leaf ALGORITHM_VALUE_SPF_OR {
                    type int32;
                }                  //(0-1)
                leaf iface {
                    type enumeration {
                        enum iface;
                    }
                }                  //iface
                leaf INTERFACE_VALUE {
                    type int32;
                }                  //(0-4294967295)
                leaf nai_adjacency {
                    type enumeration {
                        enum nai_adjacency;
                    }
                }                  //nai_adjacency
                leaf ADJ_IPV4_SRC_IDENTIFIER {
                    type inet:ipv4-address;
                }                  //A.B.C.D
                leaf ADJ_IPV4_DST_IDENTIFIER {
                    type inet:ipv4-address;
                }                  //A.B.C.D
                leaf ADJ_IPV6_SRC_IDENTIFIER {
                    type inet:ipv6-address;
                }                  //X:X::X:X
                leaf ADJ_IPV6_DST_IDENTIFIER {
                    type inet:ipv6-address;
                }                  //X:X::X:X
            }
            list EXIT {
                key "PREFIX";
                leaf PREFIX {
                    type string; 
                } 
            }
            list END {
                key "PREFIX";
                leaf PREFIX {
                    type string; 
                } 
            }
            list NO_OUTPUT_FILE {
                key "PREFIX";
                leaf PREFIX {
                    type string; 
                } 
                leaf PATH_TO_DUMP_OUTPUT {
                    type string;
                }                  //FILE
            }
        }

    }
}
