module sonic-frr-BGP_VNC_L2_GROUP_NODE {
    namespace "http://github.com/sonic-net/frr/sonic-frr-BGP_VNC_L2_GROUP_NODE";
    prefix frr-BGP_VNC_L2_GROUP_NODE;
    yang-version 1.1;

    import ietf-inet-types {
        prefix inet;
    }

    organization
        "SONiC";

    contact
        "SONiC";

    description
        "SONIC frr-BGP_VNC_L2_GROUP_NODE FRR YANG";

    revision 2024-12-23 {
        description
            "Initial revision.";
    }
    container sonic-frr-BGP_VNC_L2_GROUP_NODE {
        container BGP_VNC_L2_GROUP_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf labels {
                    type enumeration {
                        enum labels;
                    }
                }                  //labels
                leaf-list SPACE_SEPARATED_LIST_OF {
                    type int32;
                }                  //(0-1048575)...
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list RT {
                key "PREFIX";
                leaf PREFIX {
                    type string; 
                } 
                leaf RT_CHOICE_CASE {
                    type enumeration {
                        enum both;
                        enum export;
                        enum import;
                    }
                }                  //<both|export|import> ['Export+import filters', 'Export filters', 'Import filters']
                leaf BGP_IDENTIFIER {
                    type string;
                }                  //ASN:NN_OR_IP-ADDRESS:NN
            }
            list QUIT {
                key "PREFIX";
                leaf PREFIX {
                    type string; 
                } 
            }
            list LOGICAL-NETWORK-ID {
                key "PREFIX";
                leaf PREFIX {
                    type string; 
                } 
                leaf VALUE {
                    type int32;
                }                  //(0-4294967295)
            }
            list LABELS {
                key "PREFIX";
                leaf PREFIX {
                    type string; 
                } 
                leaf-list SPACE_SEPARATED_LIST_OF {
                    type int32;
                }                  //(0-1048575)...
            }
            list EXIT-VNC {
                key "PREFIX";
                leaf PREFIX {
                    type string; 
                } 
            }
            list EXIT {
                key "PREFIX";
                leaf PREFIX {
                    type string; 
                } 
            }
            list END {
                key "PREFIX";
                leaf PREFIX {
                    type string; 
                } 
            }
            list NO_OUTPUT_FILE {
                key "PREFIX";
                leaf PREFIX {
                    type string; 
                } 
                leaf PATH_TO_DUMP_OUTPUT {
                    type string;
                }                  //FILE
            }
        }

    }
}
