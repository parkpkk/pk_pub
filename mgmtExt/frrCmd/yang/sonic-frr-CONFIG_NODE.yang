module sonic-frr-CONFIG_NODE {
    namespace "http://github.com/sonic-net/frr/sonic-frr-CONFIG_NODE";
    prefix frr-CONFIG_NODE;
    yang-version 1.1;

    import ietf-inet-types {
        prefix inet;
    }

    organization
        "SONiC";

    contact
        "SONiC";

    description
        "SONIC frr-CONFIG_NODE FRR YANG";

    revision 2024-12-23 {
        description
            "Initial revision.";
    }
    container sonic-frr-CONFIG_NODE {

    }
}
