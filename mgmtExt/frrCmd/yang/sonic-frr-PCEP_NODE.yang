module sonic-frr-PCEP_NODE {
    namespace "http://github.com/sonic-net/frr/sonic-frr-PCEP_NODE";
    prefix frr-PCEP_NODE;
    yang-version 1.1;

    import ietf-inet-types {
        prefix inet;
    }

    organization
        "SONiC";

    contact
        "SONiC";

    description
        "SONIC frr-PCEP_NODE FRR YANG";

    revision 2024-12-23 {
        description
            "Initial revision.";
    }
    container sonic-frr-PCEP_NODE {
        container PCEP_NODE {
            list QUIT {
                key "PREFIX";
                leaf PREFIX {
                    type string; 
                } 
            }
            list PCE-CONFIG {
                key "PREFIX";
                leaf PREFIX {
                    type string; 
                } 
                leaf SHARED_CONFIGURATION_NAME {
                    type string;
                }                  //WORD
            }
            list PCE {
                key "PREFIX";
                leaf PREFIX {
                    type string; 
                } 
                leaf PCE_NAME {
                    type string;
                }                  //WORD
            }
            list PCC {
                key "PREFIX";
                leaf PREFIX {
                    type string; 
                } 
            }
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf pce-config {
                    type enumeration {
                        enum pce-config;
                    }
                }                  //pce-config
                leaf SHARED_CONFIGURATION_NAME {
                    type string;
                }                  //WORD
                leaf pce {
                    type enumeration {
                        enum pce;
                    }
                }                  //pce
                leaf PCE_NAME {
                    type string;
                }                  //WORD
                leaf pcc {
                    type enumeration {
                        enum pcc;
                    }
                }                  //pcc
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list EXIT {
                key "PREFIX";
                leaf PREFIX {
                    type string; 
                } 
            }
            list END {
                key "PREFIX";
                leaf PREFIX {
                    type string; 
                } 
            }
            list NO_OUTPUT_FILE {
                key "PREFIX";
                leaf PREFIX {
                    type string; 
                } 
                leaf PATH_TO_DUMP_OUTPUT {
                    type string;
                }                  //FILE
            }
        }

    }
}
