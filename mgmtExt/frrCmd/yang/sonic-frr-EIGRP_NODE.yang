module sonic-frr-EIGRP_NODE {
    namespace "http://github.com/sonic-net/frr/sonic-frr-EIGRP_NODE";
    prefix frr-EIGRP_NODE;
    yang-version 1.1;

    import ietf-inet-types {
        prefix inet;
    }

    organization
        "SONiC";

    contact
        "SONiC";

    description
        "SONIC frr-EIGRP_NODE FRR YANG";

    revision 2024-12-23 {
        description
            "Initial revision.";
    }
    container sonic-frr-EIGRP_NODE {
        container EIGRP_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf redistribute {
                    type enumeration {
                        enum redistribute;
                    }
                }                  //redistribute
                leaf FRR_REDIST_HELP_STR_EIGRPD {
                    type string;
                }                  //FRR_REDIST_STR_EIGRPD
                leaf metric {
                    type enumeration {
                        enum metric;
                    }
                }                  //metric
                leaf BANDWIDTH_METRIC_IN_KBITS {
                    type int32;
                }                  //(1-4294967295)
                leaf EIGRP_DELAY_METRIC_IN {
                    type int32;
                }                  //(0-4294967295)
                leaf COST_VALUE {
                    type int32;
                }                  //(0-255)
                leaf EIGRP_EFFECTIVE_BANDWIDTH_METRIC {
                    type int32;
                }                  //(1-255)
                leaf EIGRP_MTU_OF_THE {
                    type int32;
                }                  //(1-65535)
                leaf passive-interface {
                    type enumeration {
                        enum passive-interface;
                    }
                }                  //passive-interface
                leaf INTERFACE_TO_SUPPRESS_ON {
                    type string;
                }                  //IFNAME
                leaf network {
                    type enumeration {
                        enum network;
                    }
                }                  //network
                leaf IP_PREFIX {
                    type inet:ipv4-prefix;
                }                  //A.B.C.D/M
                leaf neighbor {
                    type enumeration {
                        enum neighbor;
                    }
                }                  //neighbor
                leaf NEIGHBOR_ADDRESS {
                    type inet:ipv4-address;
                }                  //A.B.C.D
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list VARIANCE {
                key "PREFIX";
                leaf PREFIX {
                    type string; 
                } 
                leaf METRIC_VARIANCE_MULTIPLIER {
                    type int32;
                }                  //(1-128)
            }
            list TIMERS {
                key "PREFIX";
                leaf PREFIX {
                    type string; 
                } 
                leaf active-time {
                    type enumeration {
                        enum active-time;
                    }
                }                  //active-time
                leaf ACTIVE-TIME_CHOICE_CASE {
                    type union {
                        type int32;
                        type enumeration {
                        enum disabled;
                        }
                    }
                }                  //<(1-65535)|disabled> ['Active state time limit in seconds', 'Disable time limit for active state']
            }
            list QUIT {
                key "PREFIX";
                leaf PREFIX {
                    type string; 
                } 
            }
            list METRIC {
                key "PREFIX";
                leaf PREFIX {
                    type string; 
                } 
                leaf weights {
                    type enumeration {
                        enum weights;
                    }
                }                  //weights
                leaf COST_VALUE {
                    type int32;
                }                  //(0-255)
            }
            list MAXIMUM-PATHS {
                key "PREFIX";
                leaf PREFIX {
                    type string; 
                } 
                leaf NUMBER_OF_PATHS {
                    type int32;
                }                  //(1-32)
            }
            list EXIT {
                key "PREFIX";
                leaf PREFIX {
                    type string; 
                } 
            }
            list END {
                key "PREFIX";
                leaf PREFIX {
                    type string; 
                } 
            }
            list EIGRP {
                key "PREFIX";
                leaf PREFIX {
                    type string; 
                } 
                leaf router-id {
                    type enumeration {
                        enum router-id;
                    }
                }                  //router-id
                leaf EIGRP_ROUTER-ID_IN_IP {
                    type inet:ipv4-address;
                }                  //A.B.C.D
            }
            list DISTRIBUTE-LIST {
                key "PREFIX";
                leaf PREFIX {
                    type string; 
                } 
                leaf prefix {
                    type enumeration {
                        enum prefix;
                    }
                }                  //prefix
                leaf ACCESS-LIST_NAME {
                    type string;
                }                  //ACCESSLIST_NAME
                leaf PREFIX_IN_OUT_BOUND {
                    type enumeration {
                        enum in;
                        enum out;
                    }
                }                  //<in|out> ['Filter incoming routing updates', 'Filter outgoing routing updates']
                leaf INTERFACE_NAME {
                    type string;
                }                  //WORD
                leaf ACCESS-LIST-NAME_IN_OUT_BOUND {
                    type enumeration {
                        enum in;
                        enum out;
                    }
                }                  //<in|out> ['Filter incoming routing updates', 'Filter outgoing routing updates']
            }
            list REDISTRIBUTE {
                key "PREFIX";
                leaf PREFIX {
                    type string; 
                } 
                leaf FRR_REDIST_HELP_STR_EIGRPD {
                    type string;
                }                  //FRR_REDIST_STR_EIGRPD
                leaf metric {
                    type enumeration {
                        enum metric;
                    }
                }                  //metric
                leaf BANDWIDTH_METRIC_IN_KBITS {
                    type int32;
                }                  //(1-4294967295)
                leaf EIGRP_DELAY_METRIC_IN {
                    type int32;
                }                  //(0-4294967295)
                leaf COST_VALUE {
                    type int32;
                }                  //(0-255)
                leaf EIGRP_EFFECTIVE_BANDWIDTH_METRIC {
                    type int32;
                }                  //(1-255)
                leaf EIGRP_MTU_OF_THE {
                    type int32;
                }                  //(1-65535)
            }
            list PASSIVE-INTERFACE {
                key "PREFIX";
                leaf PREFIX {
                    type string; 
                } 
                leaf INTERFACE_TO_SUPPRESS_ON {
                    type string;
                }                  //IFNAME
            }
            list NETWORK {
                key "PREFIX";
                leaf PREFIX {
                    type string; 
                } 
                leaf IP_PREFIX {
                    type inet:ipv4-prefix;
                }                  //A.B.C.D/M
            }
            list NEIGHBOR {
                key "PREFIX";
                leaf PREFIX {
                    type string; 
                } 
                leaf NEIGHBOR_ADDRESS {
                    type inet:ipv4-address;
                }                  //A.B.C.D
            }
            list NO_VARIANCE {
                key "PREFIX";
                leaf PREFIX {
                    type string; 
                } 
                leaf METRIC_VARIANCE_MULTIPLIER {
                    type int32;
                }                  //(1-128)
            }
            list NO_MAXIMUM-PATHS {
                key "PREFIX";
                leaf PREFIX {
                    type string; 
                } 
                leaf NUMBER_OF_PATHS {
                    type int32;
                }                  //(1-32)
            }
            list NO_DISTRIBUTE-LIST {
                key "PREFIX";
                leaf PREFIX {
                    type string; 
                } 
                leaf prefix {
                    type enumeration {
                        enum prefix;
                    }
                }                  //prefix
                leaf ACCESS-LIST_NAME {
                    type string;
                }                  //ACCESSLIST_NAME
                leaf PREFIX_IN_OUT_BOUND {
                    type enumeration {
                        enum in;
                        enum out;
                    }
                }                  //<in|out> ['Filter incoming routing updates', 'Filter outgoing routing updates']
                leaf INTERFACE_NAME {
                    type string;
                }                  //WORD
                leaf ACCESS-LIST-NAME_IN_OUT_BOUND {
                    type enumeration {
                        enum in;
                        enum out;
                    }
                }                  //<in|out> ['Filter incoming routing updates', 'Filter outgoing routing updates']
            }
            list NO_OUTPUT_FILE {
                key "PREFIX";
                leaf PREFIX {
                    type string; 
                } 
                leaf PATH_TO_DUMP_OUTPUT {
                    type string;
                }                  //FILE
            }
            list NO_TIMERS_ACTIVE-TIME {
                key "PREFIX";
                leaf PREFIX {
                    type string; 
                } 
                leaf CHOICE_CASE {
                    type union {
                        type int32;
                        type enumeration {
                        enum disabled;
                        }
                    }
                }                  //<(1-65535)|disabled> ['Active state time limit in seconds', 'Disable time limit for active state']
            }
            list NO_METRIC_WEIGHTS {
                key "PREFIX";
                leaf PREFIX {
                    type string; 
                } 
                leaf COST_VALUE {
                    type int32;
                }                  //(0-255)
            }
            list NO_EIGRP_ROUTER-ID {
                key "PREFIX";
                leaf PREFIX {
                    type string; 
                } 
                leaf EIGRP_ROUTER-ID_IN_IP {
                    type inet:ipv4-address;
                }                  //A.B.C.D
            }
        }

    }
}
