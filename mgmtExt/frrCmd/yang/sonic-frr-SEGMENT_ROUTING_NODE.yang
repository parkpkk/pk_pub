module sonic-frr-SEGMENT_ROUTING_NODE {
    namespace "http://github.com/sonic-net/frr/sonic-frr-SEGMENT_ROUTING_NODE";
    prefix frr-SEGMENT_ROUTING_NODE;
    yang-version 1.1;

    import ietf-inet-types {
        prefix inet;
    }

    organization
        "SONiC";

    contact
        "SONiC";

    description
        "SONIC frr-SEGMENT_ROUTING_NODE FRR YANG";

    revision 2024-12-23 {
        description
            "Initial revision.";
    }
    container sonic-frr-SEGMENT_ROUTING_NODE {
        container SEGMENT_ROUTING_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf srv6 {
                    type enumeration {
                        enum srv6;
                    }
                }                  //srv6
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list TRAFFIC-ENG {
                key "PREFIX";
                leaf PREFIX {
                    type string; 
                } 
            }
            list SRV6 {
                key "PREFIX";
                leaf PREFIX {
                    type string; 
                } 
            }
            list QUIT {
                key "PREFIX";
                leaf PREFIX {
                    type string; 
                } 
            }
            list EXIT {
                key "PREFIX";
                leaf PREFIX {
                    type string; 
                } 
            }
            list END {
                key "PREFIX";
                leaf PREFIX {
                    type string; 
                } 
            }
            list NO_OUTPUT_FILE {
                key "PREFIX";
                leaf PREFIX {
                    type string; 
                } 
                leaf PATH_TO_DUMP_OUTPUT {
                    type string;
                }                  //FILE
            }
        }

    }
}
