module sonic-frr-BABEL_NODE {
    namespace "http://github.com/sonic-net/frr/sonic-frr-BABEL_NODE";
    prefix frr-BABEL_NODE;
    yang-version 1.1;

    import ietf-inet-types {
        prefix inet;
    }

    organization
        "SONiC";

    contact
        "SONiC";

    description
        "SONIC frr-BABEL_NODE FRR YANG";

    revision 2024-12-23 {
        description
            "Initial revision.";
    }
    container sonic-frr-BABEL_NODE {
        container BABEL_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf network {
                    type enumeration {
                        enum network;
                    }
                }                  //network
                leaf INTERFACE_OR_ADDRESS {
                    type string;
                }                  //IF_OR_ADDR
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list QUIT {
                key "PREFIX";
                leaf PREFIX {
                    type string; 
                } 
            }
            list NETWORK {
                key "PREFIX";
                leaf PREFIX {
                    type string; 
                } 
                leaf INTERFACE_OR_ADDRESS {
                    type string;
                }                  //IF_OR_ADDR
            }
            list EXIT {
                key "PREFIX";
                leaf PREFIX {
                    type string; 
                } 
            }
            list END {
                key "PREFIX";
                leaf PREFIX {
                    type string; 
                } 
            }
            list DISTRIBUTE-LIST {
                key "PREFIX";
                leaf PREFIX {
                    type string; 
                } 
                leaf prefix {
                    type enumeration {
                        enum prefix;
                    }
                }                  //prefix
                leaf ACCESS-LIST_NAME {
                    type string;
                }                  //ACCESSLIST4_NAME
                leaf PREFIX_IN_OUT_BOUND {
                    type enumeration {
                        enum in;
                        enum out;
                    }
                }                  //<in|out> ['Filter incoming routing updates', 'Filter outgoing routing updates']
                leaf INTERFACE_NAME {
                    type string;
                }                  //WORD
                leaf ACCESS-LIST-NAME_IN_OUT_BOUND {
                    type enumeration {
                        enum in;
                        enum out;
                    }
                }                  //<in|out> ['Filter incoming routing updates', 'Filter outgoing routing updates']
            }
            list BABEL {
                key "PREFIX";
                leaf PREFIX {
                    type string; 
                } 
                leaf diversity {
                    type enumeration {
                        enum diversity;
                    }
                }                  //diversity
                leaf smoothing-half-life {
                    type enumeration {
                        enum smoothing-half-life;
                    }
                }                  //smoothing-half-life
                leaf SECONDS {
                    type int32;
                }                  //(0-65534)
                leaf resend-delay {
                    type enumeration {
                        enum resend-delay;
                    }
                }                  //resend-delay
                leaf MILLISECONDS {
                    type int32;
                }                  //(20-655340)
                leaf diversity-factor {
                    type enumeration {
                        enum diversity-factor;
                    }
                }                  //diversity-factor
                leaf FACTOR_IN_UNITS_OF {
                    type int32;
                }                  //(1-256)
            }
            list REDISTRIBUTE {
                key "PREFIX";
                leaf PREFIX {
                    type string; 
                } 
                leaf ipv4 {
                    type enumeration {
                        enum ipv4;
                    }
                }                  //ipv4
                leaf FRR_IP_REDIST_HELP_STR_BABELD {
                    type string;
                }                  //FRR_IP_REDIST_STR_BABELD
                leaf ipv6 {
                    type enumeration {
                        enum ipv6;
                    }
                }                  //ipv6
                leaf FRR_IP6_REDIST_HELP_STR_BABELD {
                    type string;
                }                  //FRR_IP6_REDIST_STR_BABELD
            }
            list NO_DISTRIBUTE-LIST {
                key "PREFIX";
                leaf PREFIX {
                    type string; 
                } 
                leaf prefix {
                    type enumeration {
                        enum prefix;
                    }
                }                  //prefix
                leaf ACCESS-LIST_NAME {
                    type string;
                }                  //ACCESSLIST4_NAME
                leaf PREFIX_IN_OUT_BOUND {
                    type enumeration {
                        enum in;
                        enum out;
                    }
                }                  //<in|out> ['Filter incoming routing updates', 'Filter outgoing routing updates']
                leaf INTERFACE_NAME {
                    type string;
                }                  //WORD
                leaf ACCESS-LIST-NAME_IN_OUT_BOUND {
                    type enumeration {
                        enum in;
                        enum out;
                    }
                }                  //<in|out> ['Filter incoming routing updates', 'Filter outgoing routing updates']
            }
            list NO_BABEL {
                key "PREFIX";
                leaf PREFIX {
                    type string; 
                } 
                leaf diversity {
                    type enumeration {
                        enum diversity;
                    }
                }                  //diversity
                leaf smoothing-half-life {
                    type enumeration {
                        enum smoothing-half-life;
                    }
                }                  //smoothing-half-life
                leaf SECONDS {
                    type int32;
                }                  //(0-65534)
                leaf resend-delay {
                    type enumeration {
                        enum resend-delay;
                    }
                }                  //resend-delay
                leaf MILLISECONDS {
                    type int32;
                }                  //(20-655340)
                leaf diversity-factor {
                    type enumeration {
                        enum diversity-factor;
                    }
                }                  //diversity-factor
                leaf FACTOR_IN_UNITS_OF {
                    type int32;
                }                  //(1-256)
            }
            list NO_REDISTRIBUTE {
                key "PREFIX";
                leaf PREFIX {
                    type string; 
                } 
                leaf ipv4 {
                    type enumeration {
                        enum ipv4;
                    }
                }                  //ipv4
                leaf FRR_IP_REDIST_HELP_STR_BABELD {
                    type string;
                }                  //FRR_IP_REDIST_STR_BABELD
                leaf ipv6 {
                    type enumeration {
                        enum ipv6;
                    }
                }                  //ipv6
                leaf FRR_IP6_REDIST_HELP_STR_BABELD {
                    type string;
                }                  //FRR_IP6_REDIST_STR_BABELD
            }
            list IPV6_DISTRIBUTE-LIST {
                key "PREFIX";
                leaf PREFIX {
                    type string; 
                } 
                leaf prefix {
                    type enumeration {
                        enum prefix;
                    }
                }                  //prefix
                leaf ACCESS-LIST_NAME {
                    type string;
                }                  //ACCESSLIST6_NAME
                leaf PREFIX_IN_OUT_BOUND {
                    type enumeration {
                        enum in;
                        enum out;
                    }
                }                  //<in|out> ['Filter incoming routing updates', 'Filter outgoing routing updates']
                leaf INTERFACE_NAME {
                    type string;
                }                  //WORD
                leaf ACCESS-LIST-NAME_IN_OUT_BOUND {
                    type enumeration {
                        enum in;
                        enum out;
                    }
                }                  //<in|out> ['Filter incoming routing updates', 'Filter outgoing routing updates']
            }
            list NO_OUTPUT_FILE {
                key "PREFIX";
                leaf PREFIX {
                    type string; 
                } 
                leaf PATH_TO_DUMP_OUTPUT {
                    type string;
                }                  //FILE
            }
            list NO_IPV6_DISTRIBUTE-LIST {
                key "PREFIX";
                leaf PREFIX {
                    type string; 
                } 
                leaf prefix {
                    type enumeration {
                        enum prefix;
                    }
                }                  //prefix
                leaf ACCESS-LIST_NAME {
                    type string;
                }                  //ACCESSLIST6_NAME
                leaf PREFIX_IN_OUT_BOUND {
                    type enumeration {
                        enum in;
                        enum out;
                    }
                }                  //<in|out> ['Filter incoming routing updates', 'Filter outgoing routing updates']
                leaf INTERFACE_NAME {
                    type string;
                }                  //WORD
                leaf ACCESS-LIST-NAME_IN_OUT_BOUND {
                    type enumeration {
                        enum in;
                        enum out;
                    }
                }                  //<in|out> ['Filter incoming routing updates', 'Filter outgoing routing updates']
            }
        }

    }
}
