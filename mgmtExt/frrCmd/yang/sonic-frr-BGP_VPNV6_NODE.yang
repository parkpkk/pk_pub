module sonic-frr-BGP_VPNV6_NODE {
    namespace "http://github.com/sonic-net/frr/sonic-frr-BGP_VPNV6_NODE";
    prefix frr-BGP_VPNV6_NODE;
    yang-version 1.1;

    import ietf-inet-types {
        prefix inet;
    }

    organization
        "SONiC";

    contact
        "SONiC";

    description
        "SONIC frr-BGP_VPNV6_NODE FRR YANG";

    revision 2024-12-23 {
        description
            "Initial revision.";
    }
    container sonic-frr-BGP_VPNV6_NODE {
        container BGP_VPNV6_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf network {
                    type enumeration {
                        enum network;
                    }
                }                  //network
                leaf IPV6_PREFIX {
                    type inet:ipv6-prefix;
                }                  //X:X::X:X/M
                leaf rd {
                    type enumeration {
                        enum rd;
                    }
                }                  //rd
                leaf BGP_IDENTIFIER {
                    type string;
                }                  //ASN:NN_OR_IP-ADDRESS:NN
                leaf RD_CHOICE_CASE {
                    type enumeration {
                        enum tag;
                        enum label;
                    }
                }                  //<tag|label> ['VPN 1 label (tag)', 'VPN 1 label (tag)']
                leaf LABEL_VALUE {
                    type int32;
                }                  //(0-1048575)
                leaf neighbor {
                    type enumeration {
                        enum neighbor;
                    }
                }                  //neighbor
                leaf NEIGHBOR_IP_ADDRESS {
                    type union {
                        type inet:ipv4-address;
                        type inet:ipv6-address;
                        type string;
                    }
                }                  //<A.B.C.D|X:X::X:X|WORD> ['Neighbor address', 'Neighbor IPv6 address', 'Interface name or neighbor tag']
                leaf weight {
                    type enumeration {
                        enum weight;
                    }
                }                  //weight
                leaf DEFAULT_WEIGHT {
                    type int32;
                }                  //(0-65535)
                leaf unsuppress-map {
                    type enumeration {
                        enum unsuppress-map;
                    }
                }                  //unsuppress-map
                leaf NAME_OF_ROUTE_MAP {
                    type string;
                }                  //WORD
                leaf soo {
                    type enumeration {
                        enum soo;
                    }
                }                  //soo
                leaf soft-reconfiguration_inbound {
                    type enumeration {
                        enum soft-reconfiguration_inbound;
                    }
                }                  //inbound
                leaf send-community {
                    type enumeration {
                        enum send-community;
                    }
                }                  //send-community
                leaf COMMUNITY_TYPE {
                    type enumeration {
                        enum both;
                        enum all;
                        enum extended;
                        enum standard;
                        enum large;
                    }
                }                  //<both|all|extended|standard|large> ['Send Standard and Extended Community attributes', 'Send Standard, Large and Extended Community attributes', 'Send Extended Community attributes', 'Send Standard Community attributes', 'Send Large Community attributes']
                leaf route-server-client {
                    type enumeration {
                        enum route-server-client;
                    }
                }                  //route-server-client
                leaf route-reflector-client {
                    type enumeration {
                        enum route-reflector-client;
                    }
                }                  //route-reflector-client
                leaf route-map {
                    type enumeration {
                        enum route-map;
                    }
                }                  //route-map
                leaf ROUTE-MAP_IN_OUT_BOUND {
                    type enumeration {
                        enum in;
                        enum out;
                    }
                }                  //<in|out> ['Apply map to incoming routes', 'Apply map to outbound routes']
                leaf remove-private-AS {
                    type enumeration {
                        enum remove-private-AS;
                    }
                }                  //remove-private-AS
                leaf remove-private-AS_replace-AS {
                    type enumeration {
                        enum remove-private-AS_replace-AS;
                    }
                }                  //replace-AS
                leaf prefix-list {
                    type enumeration {
                        enum prefix-list;
                    }
                }                  //prefix-list
                leaf NAME_OF_A_PREFIX {
                    type string;
                }                  //WORD
                leaf PREFIX-LIST_IN_OUT_BOUND {
                    type enumeration {
                        enum in;
                        enum out;
                    }
                }                  //<in|out> ['Filter incoming updates', 'Filter outgoing updates']
                leaf next-hop-self {
                    type enumeration {
                        enum next-hop-self;
                    }
                }                  //next-hop-self
                leaf next-hop-self_force {
                    type enumeration {
                        enum next-hop-self_force;
                    }
                }                  //force
                leaf maximum-prefix-out {
                    type enumeration {
                        enum maximum-prefix-out;
                    }
                }                  //maximum-prefix-out
                leaf MAXIMUM_NO_OF_PREFIX {
                    type int32;
                }                  //(1-4294967295)
                leaf maximum-prefix {
                    type enumeration {
                        enum maximum-prefix;
                    }
                }                  //maximum-prefix
                leaf THRESHOLD_VALUE_AT_WHICH {
                    type int32;
                }                  //(1-100)
                leaf restart {
                    type enumeration {
                        enum restart;
                    }
                }                  //restart
                leaf RESTART_INTERVAL_IN_MINUTES {
                    type int32;
                }                  //(1-65535)
                leaf warning-only {
                    type enumeration {
                        enum warning-only;
                    }
                }                  //warning-only
                leaf warning-only_force {
                    type enumeration {
                        enum warning-only_force;
                    }
                }                  //force
                leaf force {
                    type enumeration {
                        enum force;
                    }
                }                  //force
                leaf filter-list {
                    type enumeration {
                        enum filter-list;
                    }
                }                  //filter-list
                leaf AS_PATH_ACCESS-LIST_NAME {
                    type string;
                }                  //AS_PATH_FILTER_NAME
                leaf FILTER-LIST_IN_OUT_BOUND {
                    type enumeration {
                        enum in;
                        enum out;
                    }
                }                  //<in|out> ['Filter incoming routes', 'Filter outgoing routes']
                leaf distribute-list {
                    type enumeration {
                        enum distribute-list;
                    }
                }                  //distribute-list
                leaf IP_ACCESS-LIST_NAME {
                    type string;
                }                  //ACCESSLIST_NAME
                leaf DISTRIBUTE-LIST_IN_OUT_BOUND {
                    type enumeration {
                        enum in;
                        enum out;
                    }
                }                  //<in|out> ['Filter incoming updates', 'Filter outgoing updates']
                leaf disable-addpath-rx {
                    type enumeration {
                        enum disable-addpath-rx;
                    }
                }                  //disable-addpath-rx
                leaf attribute-unchanged {
                    type enumeration {
                        enum attribute-unchanged;
                    }
                }                  //attribute-unchanged
                leaf attribute-unchanged_as-path {
                    type enumeration {
                        enum attribute-unchanged_as-path;
                    }
                }                  //as-path
                leaf attribute-unchanged_next-hop {
                    type enumeration {
                        enum attribute-unchanged_next-hop;
                    }
                }                  //next-hop
                leaf attribute-unchanged_med {
                    type enumeration {
                        enum attribute-unchanged_med;
                    }
                }                  //med
                leaf as-override {
                    type enumeration {
                        enum as-override;
                    }
                }                  //as-override
                leaf allowas-in {
                    type enumeration {
                        enum allowas-in;
                    }
                }                  //allowas-in
                leaf CHOICE_CASE {
                    type union {
                        type int32;
                        type enumeration {
                        enum origin;
                        }
                    }
                }                  //<(1-10)|origin> ['Number of occurrences of AS number', 'Only accept my AS in the as-path if the route was originated in my AS']
                leaf addpath-tx-bestpath-per-AS {
                    type enumeration {
                        enum addpath-tx-bestpath-per-AS;
                    }
                }                  //addpath-tx-bestpath-per-AS
                leaf addpath-tx-all-paths {
                    type enumeration {
                        enum addpath-tx-all-paths;
                    }
                }                  //addpath-tx-all-paths
                leaf activate {
                    type enumeration {
                        enum activate;
                    }
                }                  //activate
                leaf advertise-map {
                    type enumeration {
                        enum advertise-map;
                    }
                }                  //advertise-map
                leaf NAME_OF_ADVERTISE_MAP {
                    type string;
                }                  //RMAP_NAME
                leaf ADVERTISE-MAP_ADVERTISE_OUTES_ONLY {
                    type enumeration {
                        enum exist-map;
                        enum non-exist-map;
                    }
                }                  //<exist-map|non-exist-map> ['Advertise routes only if prefixes in exist-map are installed in BGP table', 'Advertise routes only if prefixes in non-exist-map are not installed in BGP table']
                leaf NAME_OF_THE_EXIST {
                    type string;
                }                  //RMAP_NAME
                leaf accept-own {
                    type enumeration {
                        enum accept-own;
                    }
                }                  //accept-own
                leaf remove-private-AS_all {
                    type enumeration {
                        enum remove-private-AS_all;
                    }
                }                  //remove-private-AS_all
                leaf remove-private-AS_all_replace-AS {
                    type enumeration {
                        enum remove-private-AS_all_replace-AS;
                    }
                }                  //replace-AS
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list QUIT {
                key "PREFIX";
                leaf PREFIX {
                    type string; 
                } 
            }
            list NETWORK {
                key "PREFIX";
                leaf PREFIX {
                    type string; 
                } 
                leaf IPV6_PREFIX {
                    type inet:ipv6-prefix;
                }                  //X:X::X:X/M
                leaf rd {
                    type enumeration {
                        enum rd;
                    }
                }                  //rd
                leaf BGP_IDENTIFIER {
                    type string;
                }                  //ASN:NN_OR_IP-ADDRESS:NN
                leaf RD_CHOICE_CASE {
                    type enumeration {
                        enum tag;
                        enum label;
                    }
                }                  //<tag|label> ['VPN 1 label (tag)', 'VPN 1 label (tag)']
                leaf LABEL_VALUE {
                    type int32;
                }                  //(0-1048575)
                leaf route-map {
                    type enumeration {
                        enum route-map;
                    }
                }                  //route-map
                leaf ROUTE_MAP_NAME {
                    type string;
                }                  //RMAP_NAME
            }
            list NEIGHBOR {
                key "PREFIX";
                leaf PREFIX {
                    type string; 
                } 
                leaf NEIGHBOR_IP_ADDRESS {
                    type union {
                        type inet:ipv4-address;
                        type inet:ipv6-address;
                        type string;
                    }
                }                  //<A.B.C.D|X:X::X:X|WORD> ['Neighbor address', 'Neighbor IPv6 address', 'Interface name or neighbor tag']
                leaf weight {
                    type enumeration {
                        enum weight;
                    }
                }                  //weight
                leaf DEFAULT_WEIGHT {
                    type int32;
                }                  //(0-65535)
                leaf unsuppress-map {
                    type enumeration {
                        enum unsuppress-map;
                    }
                }                  //unsuppress-map
                leaf NAME_OF_ROUTE_MAP {
                    type string;
                }                  //WORD
                leaf soo {
                    type enumeration {
                        enum soo;
                    }
                }                  //soo
                leaf BGP_IDENTIFIER {
                    type string;
                }                  //ASN:NN_OR_IP-ADDRESS:NN
                leaf soft-reconfiguration_inbound {
                    type enumeration {
                        enum soft-reconfiguration_inbound;
                    }
                }                  //inbound
                leaf send-community {
                    type enumeration {
                        enum send-community;
                    }
                }                  //send-community
                leaf COMMUNITY_TYPE {
                    type enumeration {
                        enum both;
                        enum all;
                        enum extended;
                        enum standard;
                        enum large;
                    }
                }                  //<both|all|extended|standard|large> ['Send Standard and Extended Community attributes', 'Send Standard, Large and Extended Community attributes', 'Send Extended Community attributes', 'Send Standard Community attributes', 'Send Large Community attributes']
                leaf route-server-client {
                    type enumeration {
                        enum route-server-client;
                    }
                }                  //route-server-client
                leaf route-reflector-client {
                    type enumeration {
                        enum route-reflector-client;
                    }
                }                  //route-reflector-client
                leaf route-map {
                    type enumeration {
                        enum route-map;
                    }
                }                  //route-map
                leaf ROUTE-MAP_IN_OUT_BOUND {
                    type enumeration {
                        enum in;
                        enum out;
                    }
                }                  //<in|out> ['Apply map to incoming routes', 'Apply map to outbound routes']
                leaf remove-private-AS {
                    type enumeration {
                        enum remove-private-AS;
                    }
                }                  //remove-private-AS
                leaf remove-private-AS_replace-AS {
                    type enumeration {
                        enum remove-private-AS_replace-AS;
                    }
                }                  //replace-AS
                leaf prefix-list {
                    type enumeration {
                        enum prefix-list;
                    }
                }                  //prefix-list
                leaf NAME_OF_A_PREFIX {
                    type string;
                }                  //WORD
                leaf PREFIX-LIST_IN_OUT_BOUND {
                    type enumeration {
                        enum in;
                        enum out;
                    }
                }                  //<in|out> ['Filter incoming updates', 'Filter outgoing updates']
                leaf next-hop-self {
                    type enumeration {
                        enum next-hop-self;
                    }
                }                  //next-hop-self
                leaf next-hop-self_force {
                    type enumeration {
                        enum next-hop-self_force;
                    }
                }                  //force
                leaf maximum-prefix-out {
                    type enumeration {
                        enum maximum-prefix-out;
                    }
                }                  //maximum-prefix-out
                leaf MAXIMUM_NO_OF_PREFIX {
                    type int32;
                }                  //(1-4294967295)
                leaf maximum-prefix {
                    type enumeration {
                        enum maximum-prefix;
                    }
                }                  //maximum-prefix
                leaf warning-only {
                    type enumeration {
                        enum warning-only;
                    }
                }                  //warning-only
                leaf warning-only_force {
                    type enumeration {
                        enum warning-only_force;
                    }
                }                  //force
                leaf restart {
                    type enumeration {
                        enum restart;
                    }
                }                  //restart
                leaf RESTART_INTERVAL_IN_MINUTES {
                    type int32;
                }                  //(1-65535)
                leaf force {
                    type enumeration {
                        enum force;
                    }
                }                  //force
                leaf THRESHOLD_VALUE_AT_WHICH {
                    type int32;
                }                  //(1-100)
                leaf filter-list {
                    type enumeration {
                        enum filter-list;
                    }
                }                  //filter-list
                leaf AS_PATH_ACCESS-LIST_NAME {
                    type string;
                }                  //AS_PATH_FILTER_NAME
                leaf FILTER-LIST_IN_OUT_BOUND {
                    type enumeration {
                        enum in;
                        enum out;
                    }
                }                  //<in|out> ['Filter incoming routes', 'Filter outgoing routes']
                leaf distribute-list {
                    type enumeration {
                        enum distribute-list;
                    }
                }                  //distribute-list
                leaf IP_ACCESS-LIST_NAME {
                    type string;
                }                  //ACCESSLIST_NAME
                leaf DISTRIBUTE-LIST_IN_OUT_BOUND {
                    type enumeration {
                        enum in;
                        enum out;
                    }
                }                  //<in|out> ['Filter incoming updates', 'Filter outgoing updates']
                leaf disable-addpath-rx {
                    type enumeration {
                        enum disable-addpath-rx;
                    }
                }                  //disable-addpath-rx
                leaf attribute-unchanged {
                    type enumeration {
                        enum attribute-unchanged;
                    }
                }                  //attribute-unchanged
                leaf attribute-unchanged_as-path {
                    type enumeration {
                        enum attribute-unchanged_as-path;
                    }
                }                  //as-path
                leaf attribute-unchanged_next-hop {
                    type enumeration {
                        enum attribute-unchanged_next-hop;
                    }
                }                  //next-hop
                leaf attribute-unchanged_med {
                    type enumeration {
                        enum attribute-unchanged_med;
                    }
                }                  //med
                leaf as-override {
                    type enumeration {
                        enum as-override;
                    }
                }                  //as-override
                leaf allowas-in {
                    type enumeration {
                        enum allowas-in;
                    }
                }                  //allowas-in
                leaf CHOICE_CASE {
                    type union {
                        type int32;
                        type enumeration {
                        enum origin;
                        }
                    }
                }                  //<(1-10)|origin> ['Number of occurrences of AS number', 'Only accept my AS in the as-path if the route was originated in my AS']
                leaf addpath-tx-bestpath-per-AS {
                    type enumeration {
                        enum addpath-tx-bestpath-per-AS;
                    }
                }                  //addpath-tx-bestpath-per-AS
                leaf addpath-tx-all-paths {
                    type enumeration {
                        enum addpath-tx-all-paths;
                    }
                }                  //addpath-tx-all-paths
                leaf activate {
                    type enumeration {
                        enum activate;
                    }
                }                  //activate
                leaf advertise-map {
                    type enumeration {
                        enum advertise-map;
                    }
                }                  //advertise-map
                leaf NAME_OF_ADVERTISE_MAP {
                    type string;
                }                  //RMAP_NAME
                leaf ADVERTISE-MAP_ADVERTISE_OUTES_ONLY {
                    type enumeration {
                        enum exist-map;
                        enum non-exist-map;
                    }
                }                  //<exist-map|non-exist-map> ['Advertise routes only if prefixes in exist-map are installed in BGP table', 'Advertise routes only if prefixes in non-exist-map are not installed in BGP table']
                leaf NAME_OF_THE_EXIST {
                    type string;
                }                  //RMAP_NAME
                leaf accept-own {
                    type enumeration {
                        enum accept-own;
                    }
                }                  //accept-own
                leaf remove-private-AS_all {
                    type enumeration {
                        enum remove-private-AS_all;
                    }
                }                  //remove-private-AS_all
                leaf remove-private-AS_all_replace-AS {
                    type enumeration {
                        enum remove-private-AS_all_replace-AS;
                    }
                }                  //replace-AS
            }
            list EXIT-ADDRESS-FAMILY {
                key "PREFIX";
                leaf PREFIX {
                    type string; 
                } 
            }
            list EXIT {
                key "PREFIX";
                leaf PREFIX {
                    type string; 
                } 
            }
            list END {
                key "PREFIX";
                leaf PREFIX {
                    type string; 
                } 
            }
            list NO_OUTPUT_FILE {
                key "PREFIX";
                leaf PREFIX {
                    type string; 
                } 
                leaf PATH_TO_DUMP_OUTPUT {
                    type string;
                }                  //FILE
            }
            list BGP_RETAIN_ROUTE-TARGET {
                key "PREFIX";
                leaf PREFIX {
                    type string; 
                } 
                leaf all {
                    type enumeration {
                        enum all;
                    }
                }                  //all
            }
            list NO_BGP_RETAIN_ROUTE-TARGET {
                key "PREFIX";
                leaf PREFIX {
                    type string; 
                } 
                leaf all {
                    type enumeration {
                        enum all;
                    }
                }                  //all
            }
        }

    }
}
