module sonic-frr-PW_NODE {
    namespace "http://github.com/sonic-net/frr/sonic-frr-PW_NODE";
    prefix frr-PW_NODE;
    yang-version 1.1;

    import ietf-inet-types {
        prefix inet;
    }

    organization
        "SONiC";

    contact
        "SONiC";

    description
        "SONIC frr-PW_NODE FRR YANG";

    revision 2024-12-23 {
        description
            "Initial revision.";
    }
    container sonic-frr-PW_NODE {
        container PW_NODE {
            list QUIT {
                key "PREFIX";
                leaf PREFIX {
                    type string; 
                } 
            }
            list EXIT {
                key "PREFIX";
                leaf PREFIX {
                    type string; 
                } 
            }
            list END {
                key "PREFIX";
                leaf PREFIX {
                    type string; 
                } 
            }
            list NO {
                key "PREFIX";
                leaf PREFIX {
                    type string; 
                } 
                leaf neighbor {
                    type enumeration {
                        enum neighbor;
                    }
                }                  //neighbor
                leaf NEIGHBOR_IP_ADDRESS {
                    type union {
                        type inet:ipv4-address;
                        type inet:ipv6-address;
                    }
                }                  //<A.B.C.D|X:X::X:X> ['IPv4 address', 'IPv6 address']
                leaf control-word {
                    type enumeration {
                        enum control-word;
                    }
                }                  //control-word
                leaf CONTROL-WORD_CHOICE_CASE {
                    type enumeration {
                        enum exclude;
                        enum include;
                    }
                }                  //<exclude|include> ['Exclude control-word in pseudowire packets', 'Include control-word in pseudowire packets']
            }
            list NEIGHBOR {
                key "PREFIX";
                leaf PREFIX {
                    type string; 
                } 
                leaf NEIGHBOR_IP_ADDRESS {
                    type union {
                        type inet:ipv4-address;
                        type inet:ipv6-address;
                    }
                }                  //<A.B.C.D|X:X::X:X> ['IPv4 address', 'IPv6 address']
            }
            list CONTROL-WORD {
                key "PREFIX";
                leaf PREFIX {
                    type string; 
                } 
                leaf CONTROL-WORD_CHOICE_CASE {
                    type enumeration {
                        enum exclude;
                        enum include;
                    }
                }                  //<exclude|include> ['Exclude control-word in pseudowire packets', 'Include control-word in pseudowire packets']
            }
            list OUTPUT {
                key "PREFIX";
                leaf PREFIX {
                    type string; 
                } 
                leaf file {
                    type enumeration {
                        enum file;
                    }
                }                  //file
                leaf PATH_TO_DUMP_OUTPUT {
                    type string;
                }                  //FILE
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list MPLS_LABEL {
                key "PREFIX";
                leaf PREFIX {
                    type string; 
                } 
                leaf local {
                    type enumeration {
                        enum local;
                    }
                }                  //local
                leaf LOCAL_PSEUDOWIRE_LABEL {
                    type int32;
                }                  //(16-1048575)
                leaf remote {
                    type enumeration {
                        enum remote;
                    }
                }                  //remote
                leaf REMOTE_PSEUDOWIRE_LABEL {
                    type int32;
                }                  //(16-1048575)
            }
            list NO_MPLS_LABEL {
                key "PREFIX";
                leaf PREFIX {
                    type string; 
                } 
                leaf local {
                    type enumeration {
                        enum local;
                    }
                }                  //local
                leaf LOCAL_PSEUDOWIRE_LABEL {
                    type int32;
                }                  //(16-1048575)
                leaf remote {
                    type enumeration {
                        enum remote;
                    }
                }                  //remote
                leaf REMOTE_PSEUDOWIRE_LABEL {
                    type int32;
                }                  //(16-1048575)
            }
            list NO_OUTPUT_FILE {
                key "PREFIX";
                leaf PREFIX {
                    type string; 
                } 
                leaf PATH_TO_DUMP_OUTPUT {
                    type string;
                }                  //FILE
            }
        }

    }
}
