module sonic-frr-BGP_IPV6_NODE {
    namespace "http://github.com/sonic-net/frr/sonic-frr-BGP_IPV6_NODE";
    prefix frr-BGP_IPV6_NODE;
    yang-version 1.1;

    import ietf-inet-types {
        prefix inet;
    }

    organization
        "SONiC";

    contact
        "SONiC";

    description
        "SONIC frr-BGP_IPV6_NODE FRR YANG";

    revision 2024-12-23 {
        description
            "Initial revision.";
    }
    container sonic-frr-BGP_IPV6_NODE {
        container BGP_IPV6_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf table-map {
                    type enumeration {
                        enum table-map;
                    }
                }                  //table-map
                leaf NAME_OF_THE_ROUTE {
                    type string;
                }                  //WORD
                leaf redistribute {
                    type enumeration {
                        enum redistribute;
                    }
                }                  //redistribute
                leaf FRR_IP6_REDIST_HELP_STR_BGPD {
                    type string;
                }                  //FRR_IP6_REDIST_STR_BGPD
                leaf metric {
                    type enumeration {
                        enum metric;
                    }
                }                  //metric
                leaf DEFAULT_METRIC {
                    type int32;
                }                  //(0-4294967295)
                leaf route-map {
                    type enumeration {
                        enum route-map;
                    }
                }                  //route-map
                leaf POINTER_TO_ROUTE-MAP_ENTRIES {
                    type string;
                }                  //RMAP_NAME
                leaf neighbor {
                    type enumeration {
                        enum neighbor;
                    }
                }                  //neighbor
                leaf NEIGHBOR_IP_ADDRESS {
                    type union {
                        type inet:ipv4-address;
                        type inet:ipv6-address;
                        type string;
                    }
                }                  //<A.B.C.D|X:X::X:X|WORD> ['Neighbor address', 'Neighbor IPv6 address', 'Interface name or neighbor tag']
                leaf weight {
                    type enumeration {
                        enum weight;
                    }
                }                  //weight
                leaf DEFAULT_WEIGHT {
                    type int32;
                }                  //(0-65535)
                leaf unsuppress-map {
                    type enumeration {
                        enum unsuppress-map;
                    }
                }                  //unsuppress-map
                leaf NAME_OF_ROUTE_MAP {
                    type string;
                }                  //WORD
                leaf soo {
                    type enumeration {
                        enum soo;
                    }
                }                  //soo
                leaf BGP_IDENTIFIER {
                    type string;
                }                  //ASN:NN_OR_IP-ADDRESS:NN
                leaf soft-reconfiguration_inbound {
                    type enumeration {
                        enum soft-reconfiguration_inbound;
                    }
                }                  //inbound
                leaf send-community {
                    type enumeration {
                        enum send-community;
                    }
                }                  //send-community
                leaf COMMUNITY_TYPE {
                    type enumeration {
                        enum both;
                        enum all;
                        enum extended;
                        enum standard;
                        enum large;
                    }
                }                  //<both|all|extended|standard|large> ['Send Standard and Extended Community attributes', 'Send Standard, Large and Extended Community attributes', 'Send Extended Community attributes', 'Send Standard Community attributes', 'Send Large Community attributes']
                leaf route-server-client {
                    type enumeration {
                        enum route-server-client;
                    }
                }                  //route-server-client
                leaf route-reflector-client {
                    type enumeration {
                        enum route-reflector-client;
                    }
                }                  //route-reflector-client
                leaf ROUTE-MAP_IN_OUT_BOUND {
                    type enumeration {
                        enum in;
                        enum out;
                    }
                }                  //<in|out> ['Apply map to incoming routes', 'Apply map to outbound routes']
                leaf remove-private-AS {
                    type enumeration {
                        enum remove-private-AS;
                    }
                }                  //remove-private-AS
                leaf remove-private-AS_replace-AS {
                    type enumeration {
                        enum remove-private-AS_replace-AS;
                    }
                }                  //replace-AS
                leaf prefix-list {
                    type enumeration {
                        enum prefix-list;
                    }
                }                  //prefix-list
                leaf NAME_OF_A_PREFIX {
                    type string;
                }                  //WORD
                leaf PREFIX-LIST_IN_OUT_BOUND {
                    type enumeration {
                        enum in;
                        enum out;
                    }
                }                  //<in|out> ['Filter incoming updates', 'Filter outgoing updates']
                leaf nexthop-local_unchanged {
                    type enumeration {
                        enum nexthop-local_unchanged;
                    }
                }                  //unchanged
                leaf next-hop-self {
                    type enumeration {
                        enum next-hop-self;
                    }
                }                  //next-hop-self
                leaf next-hop-self_force {
                    type enumeration {
                        enum next-hop-self_force;
                    }
                }                  //force
                leaf maximum-prefix-out {
                    type enumeration {
                        enum maximum-prefix-out;
                    }
                }                  //maximum-prefix-out
                leaf MAXIMUM_NO_OF_PREFIX {
                    type int32;
                }                  //(1-4294967295)
                leaf maximum-prefix {
                    type enumeration {
                        enum maximum-prefix;
                    }
                }                  //maximum-prefix
                leaf THRESHOLD_VALUE_AT_WHICH {
                    type int32;
                }                  //(1-100)
                leaf restart {
                    type enumeration {
                        enum restart;
                    }
                }                  //restart
                leaf RESTART_INTERVAL_IN_MINUTES {
                    type int32;
                }                  //(1-65535)
                leaf warning-only {
                    type enumeration {
                        enum warning-only;
                    }
                }                  //warning-only
                leaf warning-only_force {
                    type enumeration {
                        enum warning-only_force;
                    }
                }                  //force
                leaf force {
                    type enumeration {
                        enum force;
                    }
                }                  //force
                leaf filter-list {
                    type enumeration {
                        enum filter-list;
                    }
                }                  //filter-list
                leaf AS_PATH_ACCESS-LIST_NAME {
                    type string;
                }                  //AS_PATH_FILTER_NAME
                leaf FILTER-LIST_IN_OUT_BOUND {
                    type enumeration {
                        enum in;
                        enum out;
                    }
                }                  //<in|out> ['Filter incoming routes', 'Filter outgoing routes']
                leaf distribute-list {
                    type enumeration {
                        enum distribute-list;
                    }
                }                  //distribute-list
                leaf IP_ACCESS-LIST_NAME {
                    type string;
                }                  //ACCESSLIST_NAME
                leaf DISTRIBUTE-LIST_IN_OUT_BOUND {
                    type enumeration {
                        enum in;
                        enum out;
                    }
                }                  //<in|out> ['Filter incoming updates', 'Filter outgoing updates']
                leaf disable-addpath-rx {
                    type enumeration {
                        enum disable-addpath-rx;
                    }
                }                  //disable-addpath-rx
                leaf default-originate {
                    type enumeration {
                        enum default-originate;
                    }
                }                  //default-originate
                leaf default-originate_route-map {
                    type enumeration {
                        enum default-originate_route-map;
                    }
                }                  //route-map
                leaf ROUTE-MAP_NAME {
                    type string;
                }                  //RMAP_NAME
                leaf attribute-unchanged {
                    type enumeration {
                        enum attribute-unchanged;
                    }
                }                  //attribute-unchanged
                leaf attribute-unchanged_as-path {
                    type enumeration {
                        enum attribute-unchanged_as-path;
                    }
                }                  //as-path
                leaf attribute-unchanged_next-hop {
                    type enumeration {
                        enum attribute-unchanged_next-hop;
                    }
                }                  //next-hop
                leaf attribute-unchanged_med {
                    type enumeration {
                        enum attribute-unchanged_med;
                    }
                }                  //med
                leaf as-override {
                    type enumeration {
                        enum as-override;
                    }
                }                  //as-override
                leaf allowas-in {
                    type enumeration {
                        enum allowas-in;
                    }
                }                  //allowas-in
                leaf CHOICE_CASE {
                    type union {
                        type int32;
                        type enumeration {
                        enum origin;
                        }
                    }
                }                  //<(1-10)|origin> ['Number of occurrences of AS number', 'Only accept my AS in the as-path if the route was originated in my AS']
                leaf addpath-tx-bestpath-per-AS {
                    type enumeration {
                        enum addpath-tx-bestpath-per-AS;
                    }
                }                  //addpath-tx-bestpath-per-AS
                leaf addpath-tx-all-paths {
                    type enumeration {
                        enum addpath-tx-all-paths;
                    }
                }                  //addpath-tx-all-paths
                leaf activate {
                    type enumeration {
                        enum activate;
                    }
                }                  //activate
                leaf advertise-map {
                    type enumeration {
                        enum advertise-map;
                    }
                }                  //advertise-map
                leaf NAME_OF_ADVERTISE_MAP {
                    type string;
                }                  //RMAP_NAME
                leaf ADVERTISE-MAP_ADVERTISE_OUTES_ONLY {
                    type enumeration {
                        enum exist-map;
                        enum non-exist-map;
                    }
                }                  //<exist-map|non-exist-map> ['Advertise routes only if prefixes in exist-map are installed in BGP table', 'Advertise routes only if prefixes in non-exist-map are not installed in BGP table']
                leaf NAME_OF_THE_EXIST {
                    type string;
                }                  //RMAP_NAME
                leaf remove-private-AS_all {
                    type enumeration {
                        enum remove-private-AS_all;
                    }
                }                  //remove-private-AS_all
                leaf remove-private-AS_all_replace-AS {
                    type enumeration {
                        enum remove-private-AS_all_replace-AS;
                    }
                }                  //replace-AS
                leaf capability_orf_prefix-list {
                    type enumeration {
                        enum capability_orf_prefix-list;
                    }
                }                  //prefix-list
                leaf PREFIX-LIST_FILTER_CAPABILITY {
                    type enumeration {
                        enum both;
                        enum send;
                        enum receive;
                    }
                }                  //<both|send|receive> ['Capability to 4 and RECEIVE the ORF to/from this neighbor', 'Capability to RECEIVE the ORF from this neighbor', 'Capability to 4 the ORF to this neighbor']
                leaf network {
                    type enumeration {
                        enum network;
                    }
                }                  //network
                leaf IPV6_PREFIX {
                    type inet:ipv6-prefix;
                }                  //X:X::X:X/M
                leaf label-index {
                    type enumeration {
                        enum label-index;
                    }
                }                  //label-index
                leaf LABEL_INDEX_VALUE {
                    type int32;
                }                  //(0-1048560)
                leaf aggregate-address {
                    type enumeration {
                        enum aggregate-address;
                    }
                }                  //aggregate-address
                leaf AGGREGATE_PREFIX {
                    type inet:ipv6-prefix;
                }                  //X:X::X:X/M
                leaf as-set {
                    type enumeration {
                        enum as-set;
                    }
                }                  //as-set
                leaf summary-only {
                    type enumeration {
                        enum summary-only;
                    }
                }                  //summary-only
                leaf ROUTE_MAP_NAME {
                    type string;
                }                  //RMAP_NAME
                leaf origin {
                    type enumeration {
                        enum origin;
                    }
                }                  //origin
                leaf ORIGIN_CHOICE_CASE {
                    type enumeration {
                        enum egp;
                        enum igp;
                        enum incomplete;
                    }
                }                  //<egp|igp|incomplete> ['Remote EGP', 'Local IGP', 'Unknown heritage']
                leaf matching-MED-only {
                    type enumeration {
                        enum matching-MED-only;
                    }
                }                  //matching-MED-only
                leaf suppress-map {
                    type enumeration {
                        enum suppress-map;
                    }
                }                  //suppress-map
                leaf ROUTE_MAP_WITH_THE {
                    type string;
                }                  //RMAP_NAME
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list TABLE-MAP {
                key "PREFIX";
                leaf PREFIX {
                    type string; 
                } 
                leaf NAME_OF_THE_ROUTE {
                    type string;
                }                  //WORD
            }
            list REDISTRIBUTE {
                key "PREFIX";
                leaf PREFIX {
                    type string; 
                } 
                leaf FRR_IP6_REDIST_HELP_STR_BGPD {
                    type string;
                }                  //FRR_IP6_REDIST_STR_BGPD
                leaf route-map {
                    type enumeration {
                        enum route-map;
                    }
                }                  //route-map
                leaf POINTER_TO_ROUTE-MAP_ENTRIES {
                    type string;
                }                  //RMAP_NAME
                leaf metric {
                    type enumeration {
                        enum metric;
                    }
                }                  //metric
                leaf DEFAULT_METRIC {
                    type int32;
                }                  //(0-4294967295)
            }
            list QUIT {
                key "PREFIX";
                leaf PREFIX {
                    type string; 
                } 
            }
            list NEIGHBOR {
                key "PREFIX";
                leaf PREFIX {
                    type string; 
                } 
                leaf NEIGHBOR_IP_ADDRESS {
                    type union {
                        type inet:ipv4-address;
                        type inet:ipv6-address;
                        type string;
                    }
                }                  //<A.B.C.D|X:X::X:X|WORD> ['Neighbor address', 'Neighbor IPv6 address', 'Interface name or neighbor tag']
                leaf weight {
                    type enumeration {
                        enum weight;
                    }
                }                  //weight
                leaf DEFAULT_WEIGHT {
                    type int32;
                }                  //(0-65535)
                leaf unsuppress-map {
                    type enumeration {
                        enum unsuppress-map;
                    }
                }                  //unsuppress-map
                leaf NAME_OF_ROUTE_MAP {
                    type string;
                }                  //WORD
                leaf soo {
                    type enumeration {
                        enum soo;
                    }
                }                  //soo
                leaf BGP_IDENTIFIER {
                    type string;
                }                  //ASN:NN_OR_IP-ADDRESS:NN
                leaf soft-reconfiguration_inbound {
                    type enumeration {
                        enum soft-reconfiguration_inbound;
                    }
                }                  //inbound
                leaf send-community {
                    type enumeration {
                        enum send-community;
                    }
                }                  //send-community
                leaf COMMUNITY_TYPE {
                    type enumeration {
                        enum both;
                        enum all;
                        enum extended;
                        enum standard;
                        enum large;
                    }
                }                  //<both|all|extended|standard|large> ['Send Standard and Extended Community attributes', 'Send Standard, Large and Extended Community attributes', 'Send Extended Community attributes', 'Send Standard Community attributes', 'Send Large Community attributes']
                leaf route-server-client {
                    type enumeration {
                        enum route-server-client;
                    }
                }                  //route-server-client
                leaf route-reflector-client {
                    type enumeration {
                        enum route-reflector-client;
                    }
                }                  //route-reflector-client
                leaf route-map {
                    type enumeration {
                        enum route-map;
                    }
                }                  //route-map
                leaf ROUTE-MAP_IN_OUT_BOUND {
                    type enumeration {
                        enum in;
                        enum out;
                    }
                }                  //<in|out> ['Apply map to incoming routes', 'Apply map to outbound routes']
                leaf remove-private-AS {
                    type enumeration {
                        enum remove-private-AS;
                    }
                }                  //remove-private-AS
                leaf remove-private-AS_replace-AS {
                    type enumeration {
                        enum remove-private-AS_replace-AS;
                    }
                }                  //replace-AS
                leaf prefix-list {
                    type enumeration {
                        enum prefix-list;
                    }
                }                  //prefix-list
                leaf NAME_OF_A_PREFIX {
                    type string;
                }                  //WORD
                leaf PREFIX-LIST_IN_OUT_BOUND {
                    type enumeration {
                        enum in;
                        enum out;
                    }
                }                  //<in|out> ['Filter incoming updates', 'Filter outgoing updates']
                leaf nexthop-local_unchanged {
                    type enumeration {
                        enum nexthop-local_unchanged;
                    }
                }                  //unchanged
                leaf next-hop-self {
                    type enumeration {
                        enum next-hop-self;
                    }
                }                  //next-hop-self
                leaf next-hop-self_force {
                    type enumeration {
                        enum next-hop-self_force;
                    }
                }                  //force
                leaf maximum-prefix-out {
                    type enumeration {
                        enum maximum-prefix-out;
                    }
                }                  //maximum-prefix-out
                leaf MAXIMUM_NO_OF_PREFIX {
                    type int32;
                }                  //(1-4294967295)
                leaf maximum-prefix {
                    type enumeration {
                        enum maximum-prefix;
                    }
                }                  //maximum-prefix
                leaf warning-only {
                    type enumeration {
                        enum warning-only;
                    }
                }                  //warning-only
                leaf warning-only_force {
                    type enumeration {
                        enum warning-only_force;
                    }
                }                  //force
                leaf restart {
                    type enumeration {
                        enum restart;
                    }
                }                  //restart
                leaf RESTART_INTERVAL_IN_MINUTES {
                    type int32;
                }                  //(1-65535)
                leaf force {
                    type enumeration {
                        enum force;
                    }
                }                  //force
                leaf THRESHOLD_VALUE_AT_WHICH {
                    type int32;
                }                  //(1-100)
                leaf filter-list {
                    type enumeration {
                        enum filter-list;
                    }
                }                  //filter-list
                leaf AS_PATH_ACCESS-LIST_NAME {
                    type string;
                }                  //AS_PATH_FILTER_NAME
                leaf FILTER-LIST_IN_OUT_BOUND {
                    type enumeration {
                        enum in;
                        enum out;
                    }
                }                  //<in|out> ['Filter incoming routes', 'Filter outgoing routes']
                leaf distribute-list {
                    type enumeration {
                        enum distribute-list;
                    }
                }                  //distribute-list
                leaf IP_ACCESS-LIST_NAME {
                    type string;
                }                  //ACCESSLIST_NAME
                leaf DISTRIBUTE-LIST_IN_OUT_BOUND {
                    type enumeration {
                        enum in;
                        enum out;
                    }
                }                  //<in|out> ['Filter incoming updates', 'Filter outgoing updates']
                leaf disable-addpath-rx {
                    type enumeration {
                        enum disable-addpath-rx;
                    }
                }                  //disable-addpath-rx
                leaf default-originate {
                    type enumeration {
                        enum default-originate;
                    }
                }                  //default-originate
                leaf default-originate_route-map {
                    type enumeration {
                        enum default-originate_route-map;
                    }
                }                  //route-map
                leaf ROUTE-MAP_NAME {
                    type string;
                }                  //RMAP_NAME
                leaf attribute-unchanged {
                    type enumeration {
                        enum attribute-unchanged;
                    }
                }                  //attribute-unchanged
                leaf attribute-unchanged_as-path {
                    type enumeration {
                        enum attribute-unchanged_as-path;
                    }
                }                  //as-path
                leaf attribute-unchanged_next-hop {
                    type enumeration {
                        enum attribute-unchanged_next-hop;
                    }
                }                  //next-hop
                leaf attribute-unchanged_med {
                    type enumeration {
                        enum attribute-unchanged_med;
                    }
                }                  //med
                leaf as-override {
                    type enumeration {
                        enum as-override;
                    }
                }                  //as-override
                leaf allowas-in {
                    type enumeration {
                        enum allowas-in;
                    }
                }                  //allowas-in
                leaf CHOICE_CASE {
                    type union {
                        type int32;
                        type enumeration {
                        enum origin;
                        }
                    }
                }                  //<(1-10)|origin> ['Number of occurrences of AS number', 'Only accept my AS in the as-path if the route was originated in my AS']
                leaf addpath-tx-bestpath-per-AS {
                    type enumeration {
                        enum addpath-tx-bestpath-per-AS;
                    }
                }                  //addpath-tx-bestpath-per-AS
                leaf addpath-tx-all-paths {
                    type enumeration {
                        enum addpath-tx-all-paths;
                    }
                }                  //addpath-tx-all-paths
                leaf activate {
                    type enumeration {
                        enum activate;
                    }
                }                  //activate
                leaf advertise-map {
                    type enumeration {
                        enum advertise-map;
                    }
                }                  //advertise-map
                leaf NAME_OF_ADVERTISE_MAP {
                    type string;
                }                  //RMAP_NAME
                leaf ADVERTISE-MAP_ADVERTISE_OUTES_ONLY {
                    type enumeration {
                        enum exist-map;
                        enum non-exist-map;
                    }
                }                  //<exist-map|non-exist-map> ['Advertise routes only if prefixes in exist-map are installed in BGP table', 'Advertise routes only if prefixes in non-exist-map are not installed in BGP table']
                leaf NAME_OF_THE_EXIST {
                    type string;
                }                  //RMAP_NAME
                leaf remove-private-AS_all {
                    type enumeration {
                        enum remove-private-AS_all;
                    }
                }                  //remove-private-AS_all
                leaf remove-private-AS_all_replace-AS {
                    type enumeration {
                        enum remove-private-AS_all_replace-AS;
                    }
                }                  //replace-AS
                leaf capability_orf_prefix-list {
                    type enumeration {
                        enum capability_orf_prefix-list;
                    }
                }                  //prefix-list
                leaf PREFIX-LIST_FILTER_CAPABILITY {
                    type enumeration {
                        enum both;
                        enum send;
                        enum receive;
                    }
                }                  //<both|send|receive> ['Capability to 4 and RECEIVE the ORF to/from this neighbor', 'Capability to RECEIVE the ORF from this neighbor', 'Capability to 4 the ORF to this neighbor']
            }
            list MAXIMUM-PATHS {
                key "PREFIX";
                leaf PREFIX {
                    type string; 
                } 
                leaf ibgp {
                    type enumeration {
                        enum ibgp;
                    }
                }                  //ibgp
                leaf NUMBER_OF_PATHS {
                    type int32;
                }                  //(1-256)
                leaf equal-cluster-length {
                    type enumeration {
                        enum equal-cluster-length;
                    }
                }                  //equal-cluster-length
            }
            list IMPORT {
                key "PREFIX";
                leaf PREFIX {
                    type string; 
                } 
                leaf vpn {
                    type enumeration {
                        enum vpn;
                    }
                }                  //vpn
            }
            list EXIT-ADDRESS-FAMILY {
                key "PREFIX";
                leaf PREFIX {
                    type string; 
                } 
            }
            list EXIT {
                key "PREFIX";
                leaf PREFIX {
                    type string; 
                } 
            }
            list END {
                key "PREFIX";
                leaf PREFIX {
                    type string; 
                } 
            }
            list DISTANCE {
                key "PREFIX";
                leaf PREFIX {
                    type string; 
                } 
                leaf bgp {
                    type enumeration {
                        enum bgp;
                    }
                }                  //bgp
                leaf DISTANCE_FOR_ROUTES_EXTERNAL {
                    type int32;
                }                  //(1-255)
                leaf DISTANCE_FOR_ROUTES_INTERNAL {
                    type int32;
                }                  //(1-255)
                leaf DISTANCE_FOR_LOCAL_ROUTES {
                    type int32;
                }                  //(1-255)
                leaf ADMINISTRATIVE_DISTANCE {
                    type int32;
                }                  //(1-255)
                leaf IP_SOURCE_PREFIX {
                    type inet:ipv6-prefix;
                }                  //X:X::X:X/M
                leaf ACCESS_LIST_NAME {
                    type string;
                }                  //WORD
            }
            list ROUTE-MAP {
                key "PREFIX";
                leaf PREFIX {
                    type string; 
                } 
                leaf vpn {
                    type enumeration {
                        enum vpn;
                    }
                }                  //vpn
                leaf VPN_FILTER_DIRECTION {
                    type enumeration {
                        enum import;
                        enum export;
                    }
                }                  //<import|export> ['For routes leaked from vpn to current address-family', 'For routes leaked from current address-family to vpn']
                leaf NAME_OF_ROUTE-MAP {
                    type string;
                }                  //RMAP
            }
            list NETWORK {
                key "PREFIX";
                leaf PREFIX {
                    type string; 
                } 
                leaf IPV6_PREFIX {
                    type inet:ipv6-prefix;
                }                  //X:X::X:X/M
                leaf route-map {
                    type enumeration {
                        enum route-map;
                    }
                }                  //route-map
                leaf NAME_OF_THE_ROUTE {
                    type string;
                }                  //RMAP_NAME
                leaf label-index {
                    type enumeration {
                        enum label-index;
                    }
                }                  //label-index
                leaf LABEL_INDEX_VALUE {
                    type int32;
                }                  //(0-1048560)
            }
            list AGGREGATE-ADDRESS {
                key "PREFIX";
                leaf PREFIX {
                    type string; 
                } 
                leaf AGGREGATE_PREFIX {
                    type inet:ipv6-prefix;
                }                  //X:X::X:X/M
                leaf as-set {
                    type enumeration {
                        enum as-set;
                    }
                }                  //as-set
                leaf summary-only {
                    type enumeration {
                        enum summary-only;
                    }
                }                  //summary-only
                leaf route-map {
                    type enumeration {
                        enum route-map;
                    }
                }                  //route-map
                leaf ROUTE_MAP_NAME {
                    type string;
                }                  //RMAP_NAME
                leaf origin {
                    type enumeration {
                        enum origin;
                    }
                }                  //origin
                leaf ORIGIN_CHOICE_CASE {
                    type enumeration {
                        enum egp;
                        enum igp;
                        enum incomplete;
                    }
                }                  //<egp|igp|incomplete> ['Remote EGP', 'Local IGP', 'Unknown heritage']
                leaf matching-MED-only {
                    type enumeration {
                        enum matching-MED-only;
                    }
                }                  //matching-MED-only
                leaf suppress-map {
                    type enumeration {
                        enum suppress-map;
                    }
                }                  //suppress-map
                leaf ROUTE_MAP_WITH_THE {
                    type string;
                }                  //RMAP_NAME
            }
            list ROUTE-TARGET {
                key "PREFIX";
                leaf PREFIX {
                    type string; 
                } 
                leaf vpn {
                    type enumeration {
                        enum vpn;
                    }
                }                  //vpn
                leaf VPN_CHOICE_CASE {
                    type enumeration {
                        enum import;
                        enum export;
                        enum both;
                    }
                }                  //<import|export|both> ['For routes leaked from vpn to current address-family: match any', 'For routes leaked from current address-family to vpn: set', 'both import: match any and export: set']
                leaf-list ROUTER_TARGET {
                    type string;
                }                  //RTLIST...
            }
            list EXPORT {
                key "PREFIX";
                leaf PREFIX {
                    type string; 
                } 
                leaf vpn {
                    type enumeration {
                        enum vpn;
                    }
                }                  //vpn
            }
            list NO_ROUTE-MAP {
                key "PREFIX";
                leaf PREFIX {
                    type string; 
                } 
                leaf vpn {
                    type enumeration {
                        enum vpn;
                    }
                }                  //vpn
                leaf VPN_FILTER_DIRECTION {
                    type enumeration {
                        enum import;
                        enum export;
                    }
                }                  //<import|export> ['For routes leaked from vpn to current address-family', 'For routes leaked from current address-family to vpn']
                leaf NAME_OF_ROUTE-MAP {
                    type string;
                }                  //RMAP
            }
            list NO_MAXIMUM-PATHS {
                key "PREFIX";
                leaf PREFIX {
                    type string; 
                } 
                leaf NUMBER_OF_PATHS {
                    type int32;
                }                  //(1-256)
            }
            list NO_IMPORT {
                key "PREFIX";
                leaf PREFIX {
                    type string; 
                } 
                leaf vpn {
                    type enumeration {
                        enum vpn;
                    }
                }                  //vpn
            }
            list NO_DISTANCE {
                key "PREFIX";
                leaf PREFIX {
                    type string; 
                } 
                leaf ADMINISTRATIVE_DISTANCE {
                    type int32;
                }                  //(1-255)
                leaf IP_SOURCE_PREFIX {
                    type inet:ipv6-prefix;
                }                  //X:X::X:X/M
                leaf ACCESS_LIST_NAME {
                    type string;
                }                  //WORD
            }
            list NO_ROUTE-TARGET {
                key "PREFIX";
                leaf PREFIX {
                    type string; 
                } 
                leaf vpn {
                    type enumeration {
                        enum vpn;
                    }
                }                  //vpn
                leaf VPN_CHOICE_CASE {
                    type enumeration {
                        enum import;
                        enum export;
                        enum both;
                    }
                }                  //<import|export|both> ['For routes leaked from vpn to current address-family', 'For routes leaked from current address-family to vpn', 'both import and export']
                leaf-list ROUTER_TARGET {
                    type string;
                }                  //RTLIST...
            }
            list NO_EXPORT {
                key "PREFIX";
                leaf PREFIX {
                    type string; 
                } 
                leaf vpn {
                    type enumeration {
                        enum vpn;
                    }
                }                  //vpn
            }
            list IMPORT_VRF {
                key "PREFIX";
                leaf PREFIX {
                    type string; 
                } 
                leaf route-map {
                    type enumeration {
                        enum route-map;
                    }
                }                  //route-map
                leaf NAME_OF_ROUTE-MAP {
                    type string;
                }                  //RMAP
                leaf THE_NAME_OF_THE {
                    type string;
                }                  //VIEWVRFNAME
            }
            list BGP_DAMPENING {
                key "PREFIX";
                leaf PREFIX {
                    type string; 
                } 
                leaf HALF-LIFE_TIME_FOR_THE {
                    type int32;
                }                  //(1-45)
                leaf VALUE_TO_START_REUSING {
                    type int32;
                }                  //(1-20000)
                leaf VALUE_TO_START_SUPPRESSING {
                    type int32;
                }                  //(1-50000)
                leaf MAXIMUM_DURATION_TO_SUPPRESS {
                    type int32;
                }                  //(1-255)
            }
            list SID_VPN {
                key "PREFIX";
                leaf PREFIX {
                    type string; 
                } 
                leaf export {
                    type enumeration {
                        enum export;
                    }
                }                  //export
                leaf EXPORT_CHOICE_CASE {
                    type union {
                        type int32;
                        type enumeration {
                        enum auto;
                        }
                    }
                }                  //<(1-1048575)|auto> ['Sid allocation index', 'Automatically assign a label']
            }
            list RD_VPN {
                key "PREFIX";
                leaf PREFIX {
                    type string; 
                } 
                leaf export {
                    type enumeration {
                        enum export;
                    }
                }                  //export
                leaf BGP_IDENTIFIER {
                    type string;
                }                  //ASN:NN_OR_IP-ADDRESS:NN
            }
            list LABEL_VPN {
                key "PREFIX";
                leaf PREFIX {
                    type string; 
                } 
                leaf export {
                    type enumeration {
                        enum export;
                    }
                }                  //export
                leaf EXPORT_CHOICE_CASE {
                    type union {
                        type int32;
                        type enumeration {
                        enum auto;
                        }
                    }
                }                  //<(0-1048575)|auto> ['Label Value <0-1048575>', 'Automatically assign a label']
            }
            list ROUTE-TARGET6_REDIRECT {
                key "PREFIX";
                leaf PREFIX {
                    type string; 
                } 
                leaf import {
                    type enumeration {
                        enum import;
                    }
                }                  //import
                leaf-list ROUTER_TARGET {
                    type string;
                }                  //RTLIST...
            }
            list NO_OUTPUT_FILE {
                key "PREFIX";
                leaf PREFIX {
                    type string; 
                } 
                leaf PATH_TO_DUMP_OUTPUT {
                    type string;
                }                  //FILE
            }
            list NO_MAXIMUM-PATHS_IBGP {
                key "PREFIX";
                leaf PREFIX {
                    type string; 
                } 
                leaf NUMBER_OF_PATHS {
                    type int32;
                }                  //(1-256)
                leaf equal-cluster-length {
                    type enumeration {
                        enum equal-cluster-length;
                    }
                }                  //equal-cluster-length
            }
            list NO_IMPORT_VRF {
                key "PREFIX";
                leaf PREFIX {
                    type string; 
                } 
                leaf THE_NAME_OF_THE {
                    type string;
                }                  //VIEWVRFNAME
            }
            list NO_DISTANCE_BGP {
                key "PREFIX";
                leaf PREFIX {
                    type string; 
                } 
                leaf DISTANCE_FOR_ROUTES_EXTERNAL {
                    type int32;
                }                  //(1-255)
                leaf DISTANCE_FOR_ROUTES_INTERNAL {
                    type int32;
                }                  //(1-255)
                leaf DISTANCE_FOR_LOCAL_ROUTES {
                    type int32;
                }                  //(1-255)
            }
            list NO_BGP_DAMPENING {
                key "PREFIX";
                leaf PREFIX {
                    type string; 
                } 
                leaf HALF-LIFE_TIME_FOR_THE {
                    type int32;
                }                  //(1-45)
                leaf VALUE_TO_START_REUSING {
                    type int32;
                }                  //(1-20000)
                leaf VALUE_TO_START_SUPPRESSING {
                    type int32;
                }                  //(1-50000)
                leaf MAXIMUM_DURATION_TO_SUPPRESS {
                    type int32;
                }                  //(1-255)
            }
            list NO_SID_VPN {
                key "PREFIX";
                leaf PREFIX {
                    type string; 
                } 
                leaf export {
                    type enumeration {
                        enum export;
                    }
                }                  //export
                leaf EXPORT_CHOICE_CASE {
                    type union {
                        type int32;
                        type enumeration {
                        enum auto;
                        }
                    }
                }                  //<(1-1048575)|auto> ['Sid allocation index', 'Automatically assign a label']
            }
            list NO_ROUTE-TARGET6_REDIRECT {
                key "PREFIX";
                leaf PREFIX {
                    type string; 
                } 
                leaf import {
                    type enumeration {
                        enum import;
                    }
                }                  //import
                leaf-list ROUTER_TARGET {
                    type string;
                }                  //RTLIST...
            }
            list NEXTHOP_VPN_EXPORT {
                key "PREFIX";
                leaf PREFIX {
                    type string; 
                } 
                leaf IP_ADDRESS {
                    type union {
                        type inet:ipv4-address;
                        type inet:ipv6-address;
                    }
                }                  //<A.B.C.D|X:X::X:X> ['IPv4 prefix', 'IPv6 prefix']
            }
            list NO_RD_VPN_EXPORT {
                key "PREFIX";
                leaf PREFIX {
                    type string; 
                } 
                leaf BGP_IDENTIFIER {
                    type string;
                }                  //ASN:NN_OR_IP-ADDRESS:NN
            }
            list NO_LABEL_VPN_EXPORT {
                key "PREFIX";
                leaf PREFIX {
                    type string; 
                } 
                leaf CHOICE_CASE {
                    type union {
                        type int32;
                        type enumeration {
                        enum auto;
                        }
                    }
                }                  //<(0-1048575)|auto> ['Label Value <0-1048575>', 'Automatically assign a label']
            }
            list NO_IMPORT_VRF_ROUTE-MAP {
                key "PREFIX";
                leaf PREFIX {
                    type string; 
                } 
                leaf NAME_OF_ROUTE-MAP {
                    type string;
                }                  //RMAP
            }
            list NO_NEXTHOP_VPN_EXPORT {
                key "PREFIX";
                leaf PREFIX {
                    type string; 
                } 
                leaf IP_ADDRESS {
                    type union {
                        type inet:ipv4-address;
                        type inet:ipv6-address;
                    }
                }                  //<A.B.C.D|X:X::X:X> ['IPv4 prefix', 'IPv6 prefix']
            }
        }

    }
}
