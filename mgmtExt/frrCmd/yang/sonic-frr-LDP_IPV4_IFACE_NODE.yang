module sonic-frr-LDP_IPV4_IFACE_NODE {
    namespace "http://github.com/sonic-net/frr/sonic-frr-LDP_IPV4_IFACE_NODE";
    prefix frr-LDP_IPV4_IFACE_NODE;
    yang-version 1.1;

    import ietf-inet-types {
        prefix inet;
    }

    organization
        "SONiC";

    contact
        "SONiC";

    description
        "SONIC frr-LDP_IPV4_IFACE_NODE FRR YANG";

    revision 2024-12-23 {
        description
            "Initial revision.";
    }
    container sonic-frr-LDP_IPV4_IFACE_NODE {
        container LDP_IPV4_IFACE_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list QUIT {
                key "PREFIX";
                leaf PREFIX {
                    type string; 
                } 
            }
            list EXIT {
                key "PREFIX";
                leaf PREFIX {
                    type string; 
                } 
            }
            list END {
                key "PREFIX";
                leaf PREFIX {
                    type string; 
                } 
            }
            list DISCOVERY_HELLO {
                key "PREFIX";
                leaf PREFIX {
                    type string; 
                } 
                leaf interval {
                    type enumeration {
                        enum interval;
                    }
                }                  //interval
                leaf TIME {
                    type int32;
                }                  //(1-65535)
                leaf holdtime {
                    type enumeration {
                        enum holdtime;
                    }
                }                  //holdtime
                leaf TIME_-_65535_IMPLIES {
                    type int32;
                }                  //(1-65535)
            }
            list NO_OUTPUT_FILE {
                key "PREFIX";
                leaf PREFIX {
                    type string; 
                } 
                leaf PATH_TO_DUMP_OUTPUT {
                    type string;
                }                  //FILE
            }
            list NO_DISCOVERY_HELLO {
                key "PREFIX";
                leaf PREFIX {
                    type string; 
                } 
                leaf interval {
                    type enumeration {
                        enum interval;
                    }
                }                  //interval
                leaf TIME {
                    type int32;
                }                  //(1-65535)
                leaf holdtime {
                    type enumeration {
                        enum holdtime;
                    }
                }                  //holdtime
                leaf TIME_-_65535_IMPLIES {
                    type int32;
                }                  //(1-65535)
            }
        }

    }
}
