module sonic-frr-LDP_L2VPN_NODE {
    namespace "http://github.com/sonic-net/frr/sonic-frr-LDP_L2VPN_NODE";
    prefix frr-LDP_L2VPN_NODE;
    yang-version 1.1;

    import ietf-inet-types {
        prefix inet;
    }

    organization
        "SONiC";

    contact
        "SONiC";

    description
        "SONIC frr-LDP_L2VPN_NODE FRR YANG";

    revision 2024-12-23 {
        description
            "Initial revision.";
    }
    container sonic-frr-LDP_L2VPN_NODE {
        container LDP_L2VPN_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf mtu {
                    type enumeration {
                        enum mtu;
                    }
                }                  //mtu
                leaf MAXIMUM_TRANSMISSION_UNIT_VALUE {
                    type int32;
                }                  //(1500-9180)
                leaf bridge {
                    type enumeration {
                        enum bridge;
                    }
                }                  //bridge
                leaf INTERFACE_NAME {
                    type string;
                }                  //IFNAME
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list QUIT {
                key "PREFIX";
                leaf PREFIX {
                    type string; 
                } 
            }
            list MEMBER {
                key "PREFIX";
                leaf PREFIX {
                    type string; 
                } 
                leaf pseudowire {
                    type enumeration {
                        enum pseudowire;
                    }
                }                  //pseudowire
                leaf INTERFACE_NAME {
                    type string;
                }                  //IFNAME
                leaf interface {
                    type enumeration {
                        enum interface;
                    }
                }                  //interface
            }
            list EXIT {
                key "PREFIX";
                leaf PREFIX {
                    type string; 
                } 
            }
            list END {
                key "PREFIX";
                leaf PREFIX {
                    type string; 
                } 
            }
            list VC {
                key "PREFIX";
                leaf PREFIX {
                    type string; 
                } 
                leaf type {
                    type enumeration {
                        enum type;
                    }
                }                  //type
                leaf TYPE_CHOICE_CASE {
                    type enumeration {
                        enum ethernet;
                        enum ethernet-tagged;
                    }
                }                  //<ethernet|ethernet-tagged> ['Ethernet (type 5)', 'Ethernet-tagged (type 4)']
            }
            list MTU {
                key "PREFIX";
                leaf PREFIX {
                    type string; 
                } 
                leaf MAXIMUM_TRANSMISSION_UNIT_VALUE {
                    type int32;
                }                  //(1500-9180)
            }
            list BRIDGE {
                key "PREFIX";
                leaf PREFIX {
                    type string; 
                } 
                leaf INTERFACE_NAME {
                    type string;
                }                  //IFNAME
            }
            list NO_MEMBER {
                key "PREFIX";
                leaf PREFIX {
                    type string; 
                } 
                leaf pseudowire {
                    type enumeration {
                        enum pseudowire;
                    }
                }                  //pseudowire
                leaf INTERFACE_NAME {
                    type string;
                }                  //IFNAME
                leaf interface {
                    type enumeration {
                        enum interface;
                    }
                }                  //interface
            }
            list NO_VC {
                key "PREFIX";
                leaf PREFIX {
                    type string; 
                } 
                leaf type {
                    type enumeration {
                        enum type;
                    }
                }                  //type
                leaf TYPE_CHOICE_CASE {
                    type enumeration {
                        enum ethernet;
                        enum ethernet-tagged;
                    }
                }                  //<ethernet|ethernet-tagged> ['Ethernet (type 5)', 'Ethernet-tagged (type 4)']
            }
            list NO_OUTPUT_FILE {
                key "PREFIX";
                leaf PREFIX {
                    type string; 
                } 
                leaf PATH_TO_DUMP_OUTPUT {
                    type string;
                }                  //FILE
            }
        }

    }
}
