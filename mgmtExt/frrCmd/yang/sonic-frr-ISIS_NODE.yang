module sonic-frr-ISIS_NODE {
    namespace "http://github.com/sonic-net/frr/sonic-frr-ISIS_NODE";
    prefix frr-ISIS_NODE;
    yang-version 1.1;

    import ietf-inet-types {
        prefix inet;
    }

    organization
        "SONiC";

    contact
        "SONiC";

    description
        "SONIC frr-ISIS_NODE FRR YANG";

    revision 2024-12-23 {
        description
            "Initial revision.";
    }
    container sonic-frr-ISIS_NODE {
        container ISIS_NODE {
            list TOPOLOGY {
                key "PREFIX";
                leaf PREFIX {
                    type string; 
                } 
                leaf ISIS_MT_DESCRIPTIONS {
                    type string;
                }                  //ISIS_MT_NAMES
                leaf overload {
                    type enumeration {
                        enum overload;
                    }
                }                  //overload
                leaf CHOICE_CASE {
                    type enumeration {
                        enum standard;
                        enum ipv4-unicast;
                        enum ipv4-mgmt;
                        enum ipv6-unicast;
                        enum ipv4-multicast;
                        enum ipv6-multicast;
                        enum ipv6-mgmt;
                        enum ipv6-dstsrc;
                    }
                }                  //<standard|ipv4-unicast|ipv4-mgmt|ipv6-unicast|ipv4-multicast|ipv6-multicast|ipv6-mgmt|ipv6-dstsrc> ['standard topology', 'IPv4 unicast topology', 'IPv4 management topology', 'IPv6 unicast topology', 'IPv4 multicast topology', 'IPv6 multicast topology', 'IPv6 management topology', 'IPv6 dst-src topology']
            }
            list SPF-INTERVAL {
                key "PREFIX";
                leaf PREFIX {
                    type string; 
                } 
                leaf level-1 {
                    type enumeration {
                        enum level-1;
                    }
                }                  //level-1
                leaf MINIMUM_INTERVAL_BETWEEN_CONSECUTIVE {
                    type int32;
                }                  //(1-120)
                leaf level-2 {
                    type enumeration {
                        enum level-2;
                    }
                }                  //level-2
            }
            list SPF-DELAY-IETF {
                key "PREFIX";
                leaf PREFIX {
                    type string; 
                } 
                leaf init-delay {
                    type enumeration {
                        enum init-delay;
                    }
                }                  //init-delay
                leaf INIT-DELAY {
                    type int32;
                }                  //(0-60000)
                leaf short-delay {
                    type enumeration {
                        enum short-delay;
                    }
                }                  //short-delay
                leaf SHORT-DELAY {
                    type int32;
                }                  //(0-60000)
                leaf long-delay {
                    type enumeration {
                        enum long-delay;
                    }
                }                  //long-delay
                leaf LONG-DELAY {
                    type int32;
                }                  //(0-60000)
                leaf holddown {
                    type enumeration {
                        enum holddown;
                    }
                }                  //holddown
                leaf HOLDDOWN {
                    type int32;
                }                  //(0-60000)
                leaf time-to-learn {
                    type enumeration {
                        enum time-to-learn;
                    }
                }                  //time-to-learn
                leaf TIME-TO-LEARN {
                    type int32;
                }                  //(0-60000)
            }
            list SPF {
                key "PREFIX";
                leaf PREFIX {
                    type string; 
                } 
                leaf prefix-priority {
                    type enumeration {
                        enum prefix-priority;
                    }
                }                  //prefix-priority
                leaf PREFIX-PRIORITY_CHOICE_CASE {
                    type enumeration {
                        enum critical;
                        enum high;
                        enum medium;
                    }
                }                  //<critical|high|medium> ['Specify critical priority prefixes', 'Specify high priority prefixes', 'Specify medium priority prefixes']
                leaf ACCESS-LIST_NAME {
                    type string;
                }                  //ACCESSLIST_NAME
            }
            list SET-OVERLOAD-BIT {
                key "PREFIX";
                leaf PREFIX {
                    type string; 
                } 
                leaf on-startup {
                    type enumeration {
                        enum on-startup;
                    }
                }                  //on-startup
                leaf SET_OVERLOAD_TIME_IN {
                    type int32;
                }                  //(0-86400)
            }
            list SEGMENT-ROUTING {
                key "PREFIX";
                leaf PREFIX {
                    type string; 
                } 
                leaf prefix {
                    type enumeration {
                        enum prefix;
                    }
                }                  //prefix
                leaf PREFIX_IP_PREFIX {
                    type union {
                        type inet:ipv4-prefix;
                        type inet:ipv6-prefix;
                    }
                }                  //<A.B.C.D/M|X:X::X:X/M> ['IPv4 Prefix', 'IPv6 Prefix']
                leaf absolute {
                    type enumeration {
                        enum absolute;
                    }
                }                  //absolute
                leaf THE_PREFIX_SEGMENT_ID {
                    type int32;
                }                  //(16-1048575)
                leaf CHOICE_CASE {
                    type enumeration {
                        enum no-php-flag;
                        enum explicit-null;
                    }
                }                  //<no-php-flag|explicit-null> ["Don't request Penultimate Hop Popping (PHP)", 'Upstream neighbor must replace prefix-sid with explicit null label']
                leaf n-flag-clear {
                    type enumeration {
                        enum n-flag-clear;
                    }
                }                  //n-flag-clear
                leaf index {
                    type enumeration {
                        enum index;
                    }
                }                  //index
                leaf on {
                    type enumeration {
                        enum on;
                    }
                }                  //on
                leaf node-msd {
                    type enumeration {
                        enum node-msd;
                    }
                }                  //node-msd
                leaf MAXIMUM_NUMBER_OF_LABEL {
                    type int32;
                }                  //(1-16)
                leaf global-block {
                    type enumeration {
                        enum global-block;
                    }
                }                  //global-block
                leaf THE_LOWER_BOUND_OF {
                    type int32;
                }                  //(16-1048575)
                leaf THE_UPPER_BOUND_OF {
                    type int32;
                }                  //(16-1048575)
                leaf local-block {
                    type enumeration {
                        enum local-block;
                    }
                }                  //local-block
            }
            list REDISTRIBUTE {
                key "PREFIX";
                leaf PREFIX {
                    type string; 
                } 
                leaf ipv4 {
                    type enumeration {
                        enum ipv4;
                    }
                }                  //ipv4
                leaf FRR_IP_REDIST_HELP_STR_ISISD {
                    type string;
                }                  //PROTO_IP_REDIST_STR
                leaf metric {
                    type enumeration {
                        enum metric;
                    }
                }                  //metric
                leaf ISIS_DEFAULT_METRIC {
                    type int32;
                }                  //(0-16777215)
                leaf route-map {
                    type enumeration {
                        enum route-map;
                    }
                }                  //route-map
                leaf POINTER_TO_ROUTE-MAP_ENTRIES {
                    type string;
                }                  //RMAP_NAME
                leaf ISIS_LEVEL {
                    type enumeration {
                        enum level-1;
                        enum level-2;
                    }
                }                  //<level-1|level-2> ['Redistribute into level-1', 'Redistribute into level-2']
                leaf IS-IS_DEFAULT_METRIC {
                    type int32;
                }                  //(0-16777215)
                leaf ipv6 {
                    type enumeration {
                        enum ipv6;
                    }
                }                  //ipv6
                leaf FRR_IP6_REDIST_HELP_STR_ISISD {
                    type string;
                }                  //PROTO_IP6_REDIST_STR
            }
            list QUIT {
                key "PREFIX";
                leaf PREFIX {
                    type string; 
                } 
            }
            list OUTPUT {
                key "PREFIX";
                leaf PREFIX {
                    type string; 
                } 
                leaf file {
                    type enumeration {
                        enum file;
                    }
                }                  //file
                leaf PATH_TO_DUMP_OUTPUT {
                    type string;
                }                  //FILE
            }
            list NO {
                key "PREFIX";
                leaf PREFIX {
                    type string; 
                } 
                leaf AUTHENTICATION_SCOPE {
                    type enumeration {
                        enum area-password;
                        enum domain-password;
                    }
                }                  //<area-password|domain-password> ['Configure the authentication password for an area', 'Set the authentication password for a routing domain']
                leaf topology {
                    type enumeration {
                        enum topology;
                    }
                }                  //topology
                leaf TOPOLOGY_CHOICE_CASE {
                    type enumeration {
                        enum standard;
                        enum ipv4-unicast;
                        enum ipv4-mgmt;
                        enum ipv6-unicast;
                        enum ipv4-multicast;
                        enum ipv6-multicast;
                        enum ipv6-mgmt;
                        enum ipv6-dstsrc;
                    }
                }                  //<standard|ipv4-unicast|ipv4-mgmt|ipv6-unicast|ipv4-multicast|ipv6-multicast|ipv6-mgmt|ipv6-dstsrc> ['standard topology', 'IPv4 unicast topology', 'IPv4 management topology', 'IPv6 unicast topology', 'IPv4 multicast topology', 'IPv6 multicast topology', 'IPv6 management topology', 'IPv6 dst-src topology']
                leaf overload {
                    type enumeration {
                        enum overload;
                    }
                }                  //overload
                leaf purge-originator {
                    type enumeration {
                        enum purge-originator;
                    }
                }                  //purge-originator
                leaf net {
                    type enumeration {
                        enum net;
                    }
                }                  //net
                leaf XXXXXX_XXXXX_NETWORK_ENTITY {
                    type string;
                }                  //WORD
                leaf log-adjacency-changes {
                    type enumeration {
                        enum log-adjacency-changes;
                    }
                }                  //log-adjacency-changes
            }
            list NET {
                key "PREFIX";
                leaf PREFIX {
                    type string; 
                } 
                leaf XXXXXX_XXXXX_NETWORK_ENTITY {
                    type string;
                }                  //WORD
            }
            list MPLS-TE {
                key "PREFIX";
                leaf PREFIX {
                    type string; 
                } 
                leaf on {
                    type enumeration {
                        enum on;
                    }
                }                  //on
                leaf export {
                    type enumeration {
                        enum export;
                    }
                }                  //export
            }
            list METRIC-STYLE {
                key "PREFIX";
                leaf PREFIX {
                    type string; 
                } 
                leaf METRIC-STYLE_METRIC_STYLE {
                    type enumeration {
                        enum narrow;
                        enum transition;
                        enum wide;
                    }
                }                  //<narrow|transition|wide> ['Use old style of TLVs with narrow metric', 'Send and accept both styles of TLVs during transition', 'Use new style of TLVs to carry wider metric']
            }
            list MAX-LSP-LIFETIME {
                key "PREFIX";
                leaf PREFIX {
                    type string; 
                } 
                leaf level-1 {
                    type enumeration {
                        enum level-1;
                    }
                }                  //level-1
                leaf LSP_LIFETIME_IN_SECONDS {
                    type int32;
                }                  //(350-65535)
                leaf level-2 {
                    type enumeration {
                        enum level-2;
                    }
                }                  //level-2
            }
            list LSP-TIMERS {
                key "PREFIX";
                leaf PREFIX {
                    type string; 
                } 
                leaf gen-interval {
                    type enumeration {
                        enum gen-interval;
                    }
                }                  //gen-interval
                leaf GENERATION_INTERVAL_IN_SECONDS {
                    type int32;
                }                  //(1-120)
                leaf refresh-interval {
                    type enumeration {
                        enum refresh-interval;
                    }
                }                  //refresh-interval
                leaf LSP_REFRESH_INTERVAL_IN {
                    type int32;
                }                  //(1-65235)
                leaf max-lifetime {
                    type enumeration {
                        enum max-lifetime;
                    }
                }                  //max-lifetime
                leaf MAXIMUM_LSP_LIFETIME_IN {
                    type int32;
                }                  //(350-65535)
            }
            list LSP-REFRESH-INTERVAL {
                key "PREFIX";
                leaf PREFIX {
                    type string; 
                } 
                leaf level-1 {
                    type enumeration {
                        enum level-1;
                    }
                }                  //level-1
                leaf LSP_REFRESH_INTERVAL_IN {
                    type int32;
                }                  //(1-65235)
                leaf level-2 {
                    type enumeration {
                        enum level-2;
                    }
                }                  //level-2
            }
            list LSP-MTU {
                key "PREFIX";
                leaf PREFIX {
                    type string; 
                } 
                leaf MAXIMUM_SIZE_OF_GENERATED {
                    type int32;
                }                  //(128-4352)
            }
            list LSP-GEN-INTERVAL {
                key "PREFIX";
                leaf PREFIX {
                    type string; 
                } 
                leaf level-1 {
                    type enumeration {
                        enum level-1;
                    }
                }                  //level-1
                leaf MINIMUM_INTERVAL_IN_SECONDS {
                    type int32;
                }                  //(1-120)
                leaf level-2 {
                    type enumeration {
                        enum level-2;
                    }
                }                  //level-2
            }
            list LOG-ADJACENCY-CHANGES {
                key "PREFIX";
                leaf PREFIX {
                    type string; 
                } 
            }
            list LIST {
                key "PREFIX";
                leaf PREFIX {
                    type string; 
                } 
                leaf permutations {
                    type enumeration {
                        enum permutations;
                    }
                }                  //permutations
            }
            list IS-TYPE {
                key "PREFIX";
                leaf PREFIX {
                    type string; 
                } 
                leaf IS-TYPE_ISIS_ROUTER_LEVEL {
                    type enumeration {
                        enum level-1;
                        enum level-1-2;
                        enum level-2-only;
                    }
                }                  //<level-1|level-1-2|level-2-only> ['Act as a station router only', 'Act as both a station router and an area router', 'Act as an area router only']
            }
            list FIND {
                key "PREFIX";
                leaf PREFIX {
                    type string; 
                } 
                leaf-list SEARCH_PATTERN {
                    type string;
                }                  //REGEX...
            }
            list FAST-REROUTE {
                key "PREFIX";
                leaf PREFIX {
                    type string; 
                } 
                leaf priority-limit {
                    type enumeration {
                        enum priority-limit;
                    }
                }                  //priority-limit
                leaf PRIORITY-LIMIT_CHOICE_CASE {
                    type enumeration {
                        enum critical;
                        enum high;
                        enum medium;
                    }
                }                  //<critical|high|medium> ['Compute for critical priority prefixes only', 'Compute for critical & high priority prefixes', 'Compute for critical, high & medium priority prefixes']
                leaf ISIS_LEVEL {
                    type enumeration {
                        enum level-1;
                        enum level-2;
                    }
                }                  //<level-1|level-2> ['Set priority-limit for level-1 only', 'Set priority-limit for level-2 only']
            }
            list EXIT {
                key "PREFIX";
                leaf PREFIX {
                    type string; 
                } 
            }
            list END {
                key "PREFIX";
                leaf PREFIX {
                    type string; 
                } 
            }
            list DOMAIN-PASSWORD {
                key "PREFIX";
                leaf PREFIX {
                    type string; 
                } 
                leaf DOMAIN-PASSWORD_AUTHENTICATION_TYPE {
                    type enumeration {
                        enum clear;
                        enum md5;
                    }
                }                  //<clear|md5> ['Clear-text authentication type', 'MD5 authentication type']
                leaf LEVEL-WIDE_PASSWORD {
                    type string;
                }                  //WORD
                leaf authenticate_snp {
                    type enumeration {
                        enum authenticate_snp;
                    }
                }                  //snp
                leaf SNP_PDU_MODE {
                    type enumeration {
                        enum send-only;
                        enum validate;
                    }
                }                  //<send-only|validate> ['Send but do not check PDUs on receiving', 'Send and check PDUs on receiving']
            }
            list DEFAULT-INFORMATION {
                key "PREFIX";
                leaf PREFIX {
                    type string; 
                } 
                leaf originate {
                    type enumeration {
                        enum originate;
                    }
                }                  //originate
                leaf ORIGINATE_REDISTRIBUTE_IP {
                    type enumeration {
                        enum ipv4;
                        enum ipv6;
                    }
                }                  //<ipv4|ipv6> ['Distribute default route for IPv4', 'Distribute default route for IPv6']
                leaf always {
                    type enumeration {
                        enum always;
                    }
                }                  //always
                leaf always_metric {
                    type enumeration {
                        enum always_metric;
                    }
                }                  //metric
                leaf ISIS_DEFAULT_METRIC {
                    type int32;
                }                  //(0-16777215)
                leaf always_route-map {
                    type enumeration {
                        enum always_route-map;
                    }
                }                  //route-map
                leaf POINTER_TO_ROUTE-MAP_ENTRIES {
                    type string;
                }                  //RMAP_NAME
                leaf metric {
                    type enumeration {
                        enum metric;
                    }
                }                  //metric
                leaf route-map {
                    type enumeration {
                        enum route-map;
                    }
                }                  //route-map
                leaf ISIS_LEVEL {
                    type enumeration {
                        enum level-1;
                        enum level-2;
                    }
                }                  //<level-1|level-2> ['Distribute default route into level-1', 'Distribute default route into level-2']
                leaf IS-IS_DEFAULT_METRIC {
                    type int32;
                }                  //(0-16777215)
            }
            list AREA-PASSWORD {
                key "PREFIX";
                leaf PREFIX {
                    type string; 
                } 
                leaf AREA-PASSWORD_AUTHENTICATION_TYPE {
                    type enumeration {
                        enum clear;
                        enum md5;
                    }
                }                  //<clear|md5> ['Clear-text authentication type', 'MD5 authentication type']
                leaf LEVEL-WIDE_PASSWORD {
                    type string;
                }                  //WORD
                leaf authenticate_snp {
                    type enumeration {
                        enum authenticate_snp;
                    }
                }                  //snp
                leaf SNP_PDU_MODE {
                    type enumeration {
                        enum send-only;
                        enum validate;
                    }
                }                  //<send-only|validate> ['Send but do not check PDUs on receiving', 'Send and check PDUs on receiving']
            }
            list PURGE-ORIGINATOR {
                key "PREFIX";
                leaf PREFIX {
                    type string; 
                } 
            }
            list HOSTNAME {
                key "PREFIX";
                leaf PREFIX {
                    type string; 
                } 
                leaf dynamic {
                    type enumeration {
                        enum dynamic;
                    }
                }                  //dynamic
            }
            list ATTACHED-BIT {
                key "PREFIX";
                leaf PREFIX {
                    type string; 
                } 
                leaf send {
                    type enumeration {
                        enum send;
                    }
                }                  //send
            }
            list NO_SPF-INTERVAL {
                key "PREFIX";
                leaf PREFIX {
                    type string; 
                } 
                leaf MINIMUM_INTERVAL_BETWEEN_CONSECUTIVE {
                    type int32;
                }                  //(1-120)
            }
            list NO_SPF-DELAY-IETF {
                key "PREFIX";
                leaf PREFIX {
                    type string; 
                } 
                leaf init-delay {
                    type enumeration {
                        enum init-delay;
                    }
                }                  //init-delay
                leaf INIT-DELAY {
                    type int32;
                }                  //(0-60000)
                leaf short-delay {
                    type enumeration {
                        enum short-delay;
                    }
                }                  //short-delay
                leaf SHORT-DELAY {
                    type int32;
                }                  //(0-60000)
                leaf long-delay {
                    type enumeration {
                        enum long-delay;
                    }
                }                  //long-delay
                leaf LONG-DELAY {
                    type int32;
                }                  //(0-60000)
                leaf holddown {
                    type enumeration {
                        enum holddown;
                    }
                }                  //holddown
                leaf HOLDDOWN {
                    type int32;
                }                  //(0-60000)
                leaf time-to-learn {
                    type enumeration {
                        enum time-to-learn;
                    }
                }                  //time-to-learn
                leaf TIME-TO-LEARN {
                    type int32;
                }                  //(0-60000)
            }
            list NO_SPF {
                key "PREFIX";
                leaf PREFIX {
                    type string; 
                } 
                leaf prefix-priority {
                    type enumeration {
                        enum prefix-priority;
                    }
                }                  //prefix-priority
                leaf PREFIX-PRIORITY_CHOICE_CASE {
                    type enumeration {
                        enum critical;
                        enum high;
                        enum medium;
                    }
                }                  //<critical|high|medium> ['Specify critical priority prefixes', 'Specify high priority prefixes', 'Specify medium priority prefixes']
                leaf ACCESS-LIST_NAME {
                    type string;
                }                  //ACCESSLIST_NAME
            }
            list NO_SEGMENT-ROUTING {
                key "PREFIX";
                leaf PREFIX {
                    type string; 
                } 
                leaf prefix {
                    type enumeration {
                        enum prefix;
                    }
                }                  //prefix
                leaf PREFIX_IP_PREFIX {
                    type union {
                        type inet:ipv4-prefix;
                        type inet:ipv6-prefix;
                    }
                }                  //<A.B.C.D/M|X:X::X:X/M> ['IPv4 Prefix', 'IPv6 Prefix']
                leaf absolute {
                    type enumeration {
                        enum absolute;
                    }
                }                  //absolute
                leaf THE_PREFIX_SEGMENT_ID {
                    type int32;
                }                  //(16-1048575)
                leaf CHOICE_CASE {
                    type enumeration {
                        enum no-php-flag;
                        enum explicit-null;
                    }
                }                  //<no-php-flag|explicit-null> ["Don't request Penultimate Hop Popping (PHP)", 'Upstream neighbor must replace prefix-sid with explicit null label']
                leaf n-flag-clear {
                    type enumeration {
                        enum n-flag-clear;
                    }
                }                  //n-flag-clear
                leaf index {
                    type enumeration {
                        enum index;
                    }
                }                  //index
                leaf on {
                    type enumeration {
                        enum on;
                    }
                }                  //on
            }
            list NO_MPLS-TE {
                key "PREFIX";
                leaf PREFIX {
                    type string; 
                } 
                leaf export {
                    type enumeration {
                        enum export;
                    }
                }                  //export
                leaf on {
                    type enumeration {
                        enum on;
                    }
                }                  //on
            }
            list NO_METRIC-STYLE {
                key "PREFIX";
                leaf PREFIX {
                    type string; 
                } 
                leaf narrow {
                    type enumeration {
                        enum narrow;
                    }
                }                  //narrow
                leaf transition {
                    type enumeration {
                        enum transition;
                    }
                }                  //transition
                leaf wide {
                    type enumeration {
                        enum wide;
                    }
                }                  //wide
            }
            list NO_MAX-LSP-LIFETIME {
                key "PREFIX";
                leaf PREFIX {
                    type string; 
                } 
                leaf LSP_LIFETIME_IN_SECONDS {
                    type int32;
                }                  //(350-65535)
            }
            list NO_LSP-TIMERS {
                key "PREFIX";
                leaf PREFIX {
                    type string; 
                } 
                leaf gen-interval {
                    type enumeration {
                        enum gen-interval;
                    }
                }                  //gen-interval
                leaf GENERATION_INTERVAL_IN_SECONDS {
                    type int32;
                }                  //(1-120)
                leaf refresh-interval {
                    type enumeration {
                        enum refresh-interval;
                    }
                }                  //refresh-interval
                leaf LSP_REFRESH_INTERVAL_IN {
                    type int32;
                }                  //(1-65235)
                leaf max-lifetime {
                    type enumeration {
                        enum max-lifetime;
                    }
                }                  //max-lifetime
                leaf MAXIMUM_LSP_LIFETIME_IN {
                    type int32;
                }                  //(350-65535)
            }
            list NO_LSP-REFRESH-INTERVAL {
                key "PREFIX";
                leaf PREFIX {
                    type string; 
                } 
                leaf LSP_REFRESH_INTERVAL_IN {
                    type int32;
                }                  //(1-65235)
            }
            list NO_LSP-MTU {
                key "PREFIX";
                leaf PREFIX {
                    type string; 
                } 
                leaf MAXIMUM_SIZE_OF_GENERATED {
                    type int32;
                }                  //(128-4352)
            }
            list NO_LSP-GEN-INTERVAL {
                key "PREFIX";
                leaf PREFIX {
                    type string; 
                } 
                leaf MINIMUM_INTERVAL_IN_SECONDS {
                    type int32;
                }                  //(1-120)
            }
            list NO_IS-TYPE {
                key "PREFIX";
                leaf PREFIX {
                    type string; 
                } 
                leaf ISIS_ROUTER_LEVEL {
                    type enumeration {
                        enum level-1;
                        enum level-1-2;
                        enum level-2-only;
                    }
                }                  //<level-1|level-1-2|level-2-only> ['Act as a station router only', 'Act as both a station router and an area router', 'Act as an area router only']
            }
            list NO_FAST-REROUTE {
                key "PREFIX";
                leaf PREFIX {
                    type string; 
                } 
                leaf priority-limit {
                    type enumeration {
                        enum priority-limit;
                    }
                }                  //priority-limit
                leaf PRIORITY-LIMIT_CHOICE_CASE {
                    type enumeration {
                        enum critical;
                        enum high;
                        enum medium;
                    }
                }                  //<critical|high|medium> ['Compute for critical priority prefixes only', 'Compute for critical & high priority prefixes', 'Compute for critical, high & medium priority prefixes']
                leaf ISIS_LEVEL {
                    type enumeration {
                        enum level-1;
                        enum level-2;
                    }
                }                  //<level-1|level-2> ['Set priority-limit for level-1 only', 'Set priority-limit for level-2 only']
            }
            list NO_REDISTRIBUTE {
                key "PREFIX";
                leaf PREFIX {
                    type string; 
                } 
                leaf ipv4 {
                    type enumeration {
                        enum ipv4;
                    }
                }                  //ipv4
                leaf FRR_IP_REDIST_HELP_STR_ISISD {
                    type string;
                }                  //PROTO_IP_REDIST_STR
                leaf IPV4_ISIS_LEVEL {
                    type enumeration {
                        enum level-1;
                        enum level-2;
                    }
                }                  //<level-1|level-2> ['Redistribute into level-1', 'Redistribute into level-2']
                leaf metric {
                    type enumeration {
                        enum metric;
                    }
                }                  //metric
                leaf IS-IS_DEFAULT_METRIC {
                    type int32;
                }                  //(0-16777215)
                leaf route-map {
                    type enumeration {
                        enum route-map;
                    }
                }                  //route-map
                leaf POINTER_TO_ROUTE-MAP_ENTRIES {
                    type string;
                }                  //RMAP_NAME
                leaf ipv6 {
                    type enumeration {
                        enum ipv6;
                    }
                }                  //ipv6
                leaf FRR_IP6_REDIST_HELP_STR_ISISD {
                    type string;
                }                  //PROTO_IP6_REDIST_STR
                leaf IPV6_ISIS_LEVEL {
                    type enumeration {
                        enum level-1;
                        enum level-2;
                    }
                }                  //<level-1|level-2> ['Redistribute into level-1', 'Redistribute into level-2']
                leaf ISIS_LEVEL {
                    type enumeration {
                        enum level-1;
                        enum level-2;
                    }
                }                  //<level-1|level-2> ['Redistribute into level-1', 'Redistribute into level-2']
            }
            list NO_HOSTNAME {
                key "PREFIX";
                leaf PREFIX {
                    type string; 
                } 
                leaf dynamic {
                    type enumeration {
                        enum dynamic;
                    }
                }                  //dynamic
            }
            list NO_DEFAULT-INFORMATION {
                key "PREFIX";
                leaf PREFIX {
                    type string; 
                } 
                leaf originate {
                    type enumeration {
                        enum originate;
                    }
                }                  //originate
                leaf ORIGINATE_REDISTRIBUTE_IP {
                    type enumeration {
                        enum ipv4;
                        enum ipv6;
                    }
                }                  //<ipv4|ipv6> ['Distribute default route for IPv4', 'Distribute default route for IPv6']
                leaf ORIGINATE-REDISTRIBUTE-IP_ISIS_LEVEL {
                    type enumeration {
                        enum level-1;
                        enum level-2;
                    }
                }                  //<level-1|level-2> ['Distribute default route into level-1', 'Distribute default route into level-2']
                leaf always {
                    type enumeration {
                        enum always;
                    }
                }                  //always
                leaf always_metric {
                    type enumeration {
                        enum always_metric;
                    }
                }                  //metric
                leaf IS-IS_DEFAULT_METRIC {
                    type int32;
                }                  //(0-16777215)
                leaf always_route-map {
                    type enumeration {
                        enum always_route-map;
                    }
                }                  //route-map
                leaf POINTER_TO_ROUTE-MAP_ENTRIES {
                    type string;
                }                  //RMAP_NAME
                leaf metric {
                    type enumeration {
                        enum metric;
                    }
                }                  //metric
                leaf route-map {
                    type enumeration {
                        enum route-map;
                    }
                }                  //route-map
            }
            list NO_ATTACHED-BIT {
                key "PREFIX";
                leaf PREFIX {
                    type string; 
                } 
                leaf send {
                    type enumeration {
                        enum send;
                    }
                }                  //send
            }
            list MPLS-TE_ROUTER-ADDRESS {
                key "PREFIX";
                leaf PREFIX {
                    type string; 
                } 
                leaf ipv6 {
                    type enumeration {
                        enum ipv6;
                    }
                }                  //ipv6
                leaf MPLS-TE_ROUTER_ADDRESS_IN {
                    type inet:ipv6-address;
                }                  //X:X::X:X
            }
            list MPLS-TE_INTER-AS {
                key "PREFIX";
                leaf PREFIX {
                    type string; 
                } 
                leaf level-1 {
                    type enumeration {
                        enum level-1;
                    }
                }                  //level-1
                leaf level-1-2 {
                    type enumeration {
                        enum level-1-2;
                    }
                }                  //level-1-2
                leaf level-2-only {
                    type enumeration {
                        enum level-2-only;
                    }
                }                  //level-2-only
            }
            list MPLS_LDP-SYNC {
                key "PREFIX";
                leaf PREFIX {
                    type string; 
                } 
                leaf holddown {
                    type enumeration {
                        enum holddown;
                    }
                }                  //holddown
                leaf TIME_IN_SECONDS {
                    type int32;
                }                  //(0-10000)
            }
            list LSP-TIMERS_LEVEL-1 {
                key "PREFIX";
                leaf PREFIX {
                    type string; 
                } 
                leaf gen-interval {
                    type enumeration {
                        enum gen-interval;
                    }
                }                  //gen-interval
                leaf GENERATION_INTERVAL_IN_SECONDS {
                    type int32;
                }                  //(1-120)
                leaf refresh-interval {
                    type enumeration {
                        enum refresh-interval;
                    }
                }                  //refresh-interval
                leaf LSP_REFRESH_INTERVAL_IN {
                    type int32;
                }                  //(1-65235)
                leaf max-lifetime {
                    type enumeration {
                        enum max-lifetime;
                    }
                }                  //max-lifetime
                leaf MAXIMUM_LSP_LIFETIME_IN {
                    type int32;
                }                  //(350-65535)
            }
            list LSP-TIMERS_LEVEL-2 {
                key "PREFIX";
                leaf PREFIX {
                    type string; 
                } 
                leaf gen-interval {
                    type enumeration {
                        enum gen-interval;
                    }
                }                  //gen-interval
                leaf GENERATION_INTERVAL_IN_SECONDS {
                    type int32;
                }                  //(1-120)
                leaf refresh-interval {
                    type enumeration {
                        enum refresh-interval;
                    }
                }                  //refresh-interval
                leaf LSP_REFRESH_INTERVAL_IN {
                    type int32;
                }                  //(1-65235)
                leaf max-lifetime {
                    type enumeration {
                        enum max-lifetime;
                    }
                }                  //max-lifetime
                leaf MAXIMUM_LSP_LIFETIME_IN {
                    type int32;
                }                  //(350-65535)
            }
            list FAST-REROUTE_REMOTE-LFA {
                key "PREFIX";
                leaf PREFIX {
                    type string; 
                } 
                leaf prefix-list {
                    type enumeration {
                        enum prefix-list;
                    }
                }                  //prefix-list
                leaf PREFIX-LIST_NAME {
                    type string;
                }                  //WORD
                leaf ISIS_LEVEL {
                    type enumeration {
                        enum level-1;
                        enum level-2;
                    }
                }                  //<level-1|level-2> ['Enable router ID filtering for level-1 only', 'Enable router ID filtering for level-2 only']
            }
            list FAST-REROUTE_LFA {
                key "PREFIX";
                leaf PREFIX {
                    type string; 
                } 
                leaf tiebreaker {
                    type enumeration {
                        enum tiebreaker;
                    }
                }                  //tiebreaker
                leaf TIEBREAKER_CHOICE_CASE {
                    type enumeration {
                        enum downstream;
                        enum lowest-backup-metric;
                        enum node-protecting;
                    }
                }                  //<downstream|lowest-backup-metric|node-protecting> ['Prefer backup path via downstream node', 'Prefer backup path with lowest total metric', 'Prefer node protecting backup path']
                leaf index {
                    type enumeration {
                        enum index;
                    }
                }                  //index
                leaf INDEX {
                    type int32;
                }                  //(1-255)
                leaf ISIS_LEVEL {
                    type enumeration {
                        enum level-1;
                        enum level-2;
                    }
                }                  //<level-1|level-2> ['Configure tiebreaker for level-1 only', 'Configure tiebreaker for level-2 only']
            }
            list ATTACHED-BIT_RECEIVE {
                key "PREFIX";
                leaf PREFIX {
                    type string; 
                } 
                leaf ignore {
                    type enumeration {
                        enum ignore;
                    }
                }                  //ignore
            }
            list NO_SPF-INTERVAL_LEVEL-1 {
                key "PREFIX";
                leaf PREFIX {
                    type string; 
                } 
                leaf MINIMUM_INTERVAL_BETWEEN_CONSECUTIVE {
                    type int32;
                }                  //(1-120)
            }
            list NO_SPF-INTERVAL_LEVEL-2 {
                key "PREFIX";
                leaf PREFIX {
                    type string; 
                } 
                leaf MINIMUM_INTERVAL_BETWEEN_CONSECUTIVE {
                    type int32;
                }                  //(1-120)
            }
            list NO_SET-OVERLOAD-BIT_ON-STARTUP {
                key "PREFIX";
                leaf PREFIX {
                    type string; 
                } 
                leaf SET_OVERLOAD_TIME_IN {
                    type int32;
                }                  //(0-86400)
            }
            list NO_SEGMENT-ROUTING_NODE-MSD {
                key "PREFIX";
                leaf PREFIX {
                    type string; 
                } 
                leaf MAXIMUM_NUMBER_OF_LABEL {
                    type int32;
                }                  //(1-16)
            }
            list NO_SEGMENT-ROUTING_GLOBAL-BLOCK {
                key "PREFIX";
                leaf PREFIX {
                    type string; 
                } 
                leaf THE_LOWER_BOUND_OF {
                    type int32;
                }                  //(16-1048575)
                leaf THE_UPPER_BOUND_OF {
                    type int32;
                }                  //(16-1048575)
                leaf local-block {
                    type enumeration {
                        enum local-block;
                    }
                }                  //local-block
            }
            list NO_OUTPUT_FILE {
                key "PREFIX";
                leaf PREFIX {
                    type string; 
                } 
                leaf PATH_TO_DUMP_OUTPUT {
                    type string;
                }                  //FILE
            }
            list NO_MPLS-TE_ROUTER-ADDRESS {
                key "PREFIX";
                leaf PREFIX {
                    type string; 
                } 
                leaf MPLS-TE_ROUTER_ADDRESS_IN {
                    type inet:ipv4-address;
                }                  //A.B.C.D
            }
            list NO_MPLS-TE_INTER-AS {
                key "PREFIX";
                leaf PREFIX {
                    type string; 
                } 
                leaf level-1 {
                    type enumeration {
                        enum level-1;
                    }
                }                  //level-1
                leaf level-1-2 {
                    type enumeration {
                        enum level-1-2;
                    }
                }                  //level-1-2
                leaf level-2-only {
                    type enumeration {
                        enum level-2-only;
                    }
                }                  //level-2-only
            }
            list NO_MAX-LSP-LIFETIME_LEVEL-1 {
                key "PREFIX";
                leaf PREFIX {
                    type string; 
                } 
                leaf LSP_LIFETIME_IN_SECONDS {
                    type int32;
                }                  //(350-65535)
            }
            list NO_MAX-LSP-LIFETIME_LEVEL-2 {
                key "PREFIX";
                leaf PREFIX {
                    type string; 
                } 
                leaf LSP_LIFETIME_IN_SECONDS {
                    type int32;
                }                  //(350-65535)
            }
            list NO_LSP-TIMERS_LEVEL-1 {
                key "PREFIX";
                leaf PREFIX {
                    type string; 
                } 
                leaf gen-interval {
                    type enumeration {
                        enum gen-interval;
                    }
                }                  //gen-interval
                leaf GENERATION_INTERVAL_IN_SECONDS {
                    type int32;
                }                  //(1-120)
                leaf refresh-interval {
                    type enumeration {
                        enum refresh-interval;
                    }
                }                  //refresh-interval
                leaf LSP_REFRESH_INTERVAL_IN {
                    type int32;
                }                  //(1-65235)
                leaf max-lifetime {
                    type enumeration {
                        enum max-lifetime;
                    }
                }                  //max-lifetime
                leaf MAXIMUM_LSP_LIFETIME_IN {
                    type int32;
                }                  //(350-65535)
            }
            list NO_LSP-TIMERS_LEVEL-2 {
                key "PREFIX";
                leaf PREFIX {
                    type string; 
                } 
                leaf gen-interval {
                    type enumeration {
                        enum gen-interval;
                    }
                }                  //gen-interval
                leaf GENERATION_INTERVAL_IN_SECONDS {
                    type int32;
                }                  //(1-120)
                leaf refresh-interval {
                    type enumeration {
                        enum refresh-interval;
                    }
                }                  //refresh-interval
                leaf LSP_REFRESH_INTERVAL_IN {
                    type int32;
                }                  //(1-65235)
                leaf max-lifetime {
                    type enumeration {
                        enum max-lifetime;
                    }
                }                  //max-lifetime
                leaf MAXIMUM_LSP_LIFETIME_IN {
                    type int32;
                }                  //(350-65535)
            }
            list NO_LSP-REFRESH-INTERVAL_LEVEL-1 {
                key "PREFIX";
                leaf PREFIX {
                    type string; 
                } 
                leaf LSP_REFRESH_INTERVAL_IN {
                    type int32;
                }                  //(1-65235)
            }
            list NO_LSP-REFRESH-INTERVAL_LEVEL-2 {
                key "PREFIX";
                leaf PREFIX {
                    type string; 
                } 
                leaf LSP_REFRESH_INTERVAL_IN {
                    type int32;
                }                  //(1-65235)
            }
            list NO_LSP-GEN-INTERVAL_LEVEL-1 {
                key "PREFIX";
                leaf PREFIX {
                    type string; 
                } 
                leaf MINIMUM_INTERVAL_IN_SECONDS {
                    type int32;
                }                  //(1-120)
            }
            list NO_LSP-GEN-INTERVAL_LEVEL-2 {
                key "PREFIX";
                leaf PREFIX {
                    type string; 
                } 
                leaf MINIMUM_INTERVAL_IN_SECONDS {
                    type int32;
                }                  //(1-120)
            }
            list NO_FAST-REROUTE_LFA {
                key "PREFIX";
                leaf PREFIX {
                    type string; 
                } 
                leaf tiebreaker {
                    type enumeration {
                        enum tiebreaker;
                    }
                }                  //tiebreaker
                leaf TIEBREAKER_CHOICE_CASE {
                    type enumeration {
                        enum downstream;
                        enum lowest-backup-metric;
                        enum node-protecting;
                    }
                }                  //<downstream|lowest-backup-metric|node-protecting> ['Prefer backup path via downstream node', 'Prefer backup path with lowest total metric', 'Prefer node protecting backup path']
                leaf index {
                    type enumeration {
                        enum index;
                    }
                }                  //index
                leaf INDEX {
                    type int32;
                }                  //(1-255)
                leaf ISIS_LEVEL {
                    type enumeration {
                        enum level-1;
                        enum level-2;
                    }
                }                  //<level-1|level-2> ['Configure tiebreaker for level-1 only', 'Configure tiebreaker for level-2 only']
            }
            list NO_ATTACHED-BIT_RECEIVE {
                key "PREFIX";
                leaf PREFIX {
                    type string; 
                } 
                leaf ignore {
                    type enumeration {
                        enum ignore;
                    }
                }                  //ignore
            }
            list FAST-REROUTE_LOAD-SHARING_DISABLE {
                key "PREFIX";
                leaf PREFIX {
                    type string; 
                } 
                leaf ISIS_LEVEL {
                    type enumeration {
                        enum level-1;
                        enum level-2;
                    }
                }                  //<level-1|level-2> ['Disable load sharing for level-1 only', 'Disable load sharing for level-2 only']
            }
            list NO_MPLS-TE_ROUTER-ADDRESS_IPV6 {
                key "PREFIX";
                leaf PREFIX {
                    type string; 
                } 
                leaf MPLS-TE_ROUTER_ADDRESS_IN {
                    type inet:ipv6-address;
                }                  //X:X::X:X
            }
            list NO_MPLS_LDP-SYNC_HOLDDOWN {
                key "PREFIX";
                leaf PREFIX {
                    type string; 
                } 
                leaf TIME_IN_SECONDS {
                    type int32;
                }                  //(1-10000)
            }
            list NO_FAST-REROUTE_REMOTE-LFA_PREFIX-LIST {
                key "PREFIX";
                leaf PREFIX {
                    type string; 
                } 
                leaf PREFIX-LIST_NAME {
                    type string;
                }                  //WORD
                leaf ISIS_LEVEL {
                    type enumeration {
                        enum level-1;
                        enum level-2;
                    }
                }                  //<level-1|level-2> ['Enable router ID filtering for level-1 only', 'Enable router ID filtering for level-2 only']
            }
            list NO_FAST-REROUTE_LOAD-SHARING_DISABLE {
                key "PREFIX";
                leaf PREFIX {
                    type string; 
                } 
                leaf ISIS_LEVEL {
                    type enumeration {
                        enum level-1;
                        enum level-2;
                    }
                }                  //<level-1|level-2> ['Disable load sharing for level-1 only', 'Disable load sharing for level-2 only']
            }
        }

    }
}
