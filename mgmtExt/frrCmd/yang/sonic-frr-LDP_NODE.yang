module sonic-frr-LDP_NODE {
    namespace "http://github.com/sonic-net/frr/sonic-frr-LDP_NODE";
    prefix frr-LDP_NODE;
    yang-version 1.1;

    import ietf-inet-types {
        prefix inet;
    }

    organization
        "SONiC";

    contact
        "SONiC";

    description
        "SONIC frr-LDP_NODE FRR YANG";

    revision 2024-12-23 {
        description
            "Initial revision.";
    }
    container sonic-frr-LDP_NODE {
        container LDP_NODE {
            list QUIT {
                key "PREFIX";
                leaf PREFIX {
                    type string; 
                } 
            }
            list NO {
                key "PREFIX";
                leaf PREFIX {
                    type string; 
                } 
                leaf address-family {
                    type enumeration {
                        enum address-family;
                    }
                }                  //address-family
                leaf ADDRESS-FAMILY_REDISTRIBUTE_IP {
                    type enumeration {
                        enum ipv4;
                        enum ipv6;
                    }
                }                  //<ipv4|ipv6> ['IPv4', 'IPv6']
                leaf wait-for-sync {
                    type enumeration {
                        enum wait-for-sync;
                    }
                }                  //wait-for-sync
                leaf TIME {
                    type int32;
                }                  //(1-10000)
                leaf router-id {
                    type enumeration {
                        enum router-id;
                    }
                }                  //router-id
                leaf LSR_ID {
                    type inet:ipv4-address;
                }                  //A.B.C.D
                leaf ordered-control {
                    type enumeration {
                        enum ordered-control;
                    }
                }                  //ordered-control
                leaf neighbor {
                    type enumeration {
                        enum neighbor;
                    }
                }                  //neighbor
                leaf LDP_ID_OF_NEIGHBOR {
                    type inet:ipv4-address;
                }                  //A.B.C.D
                leaf ttl-security {
                    type enumeration {
                        enum ttl-security;
                    }
                }                  //ttl-security
                leaf ttl-security_disable {
                    type enumeration {
                        enum ttl-security_disable;
                    }
                }                  //disable
                leaf ttl-security_hops {
                    type enumeration {
                        enum ttl-security_hops;
                    }
                }                  //hops
                leaf MAXIMUM_NUMBER_OF_HOPS {
                    type int32;
                }                  //(1-254)
                leaf session_holdtime {
                    type enumeration {
                        enum session_holdtime;
                    }
                }                  //holdtime
                leaf password {
                    type enumeration {
                        enum password;
                    }
                }                  //password
                leaf THE_PASSWORD {
                    type string;
                }                  //WORD
            }
            list EXIT {
                key "PREFIX";
                leaf PREFIX {
                    type string; 
                } 
            }
            list END {
                key "PREFIX";
                leaf PREFIX {
                    type string; 
                } 
            }
            list ADDRESS-FAMILY {
                key "PREFIX";
                leaf PREFIX {
                    type string; 
                } 
                leaf ipv6 {
                    type enumeration {
                        enum ipv6;
                    }
                }                  //ipv6
                leaf ipv4 {
                    type enumeration {
                        enum ipv4;
                    }
                }                  //ipv4
            }
            list WAIT-FOR-SYNC {
                key "PREFIX";
                leaf PREFIX {
                    type string; 
                } 
                leaf TIME {
                    type int32;
                }                  //(1-10000)
            }
            list ROUTER-ID {
                key "PREFIX";
                leaf PREFIX {
                    type string; 
                } 
                leaf LSR_ID {
                    type inet:ipv4-address;
                }                  //A.B.C.D
            }
            list ORDERED-CONTROL {
                key "PREFIX";
                leaf PREFIX {
                    type string; 
                } 
            }
            list NEIGHBOR {
                key "PREFIX";
                leaf PREFIX {
                    type string; 
                } 
                leaf LDP_ID_OF_NEIGHBOR {
                    type inet:ipv4-address;
                }                  //A.B.C.D
                leaf ttl-security {
                    type enumeration {
                        enum ttl-security;
                    }
                }                  //ttl-security
                leaf ttl-security_disable {
                    type enumeration {
                        enum ttl-security_disable;
                    }
                }                  //disable
                leaf ttl-security_hops {
                    type enumeration {
                        enum ttl-security_hops;
                    }
                }                  //hops
                leaf MAXIMUM_NUMBER_OF_HOPS {
                    type int32;
                }                  //(1-254)
                leaf session_holdtime {
                    type enumeration {
                        enum session_holdtime;
                    }
                }                  //holdtime
                leaf TIME {
                    type int32;
                }                  //(15-65535)
                leaf password {
                    type enumeration {
                        enum password;
                    }
                }                  //password
                leaf THE_PASSWORD {
                    type string;
                }                  //WORD
            }
            list INSTALL {
                key "PREFIX";
                leaf PREFIX {
                    type string; 
                } 
                leaf allow-broken-lsps {
                    type enumeration {
                        enum allow-broken-lsps;
                    }
                }                  //allow-broken-lsps
            }
            list DUAL-STACK {
                key "PREFIX";
                leaf PREFIX {
                    type string; 
                } 
                leaf cisco-interop {
                    type enumeration {
                        enum cisco-interop;
                    }
                }                  //cisco-interop
            }
            list OUTPUT {
                key "PREFIX";
                leaf PREFIX {
                    type string; 
                } 
                leaf file {
                    type enumeration {
                        enum file;
                    }
                }                  //file
                leaf PATH_TO_DUMP_OUTPUT {
                    type string;
                }                  //FILE
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list NO_INSTALL {
                key "PREFIX";
                leaf PREFIX {
                    type string; 
                } 
                leaf allow-broken-lsps {
                    type enumeration {
                        enum allow-broken-lsps;
                    }
                }                  //allow-broken-lsps
            }
            list NO_DUAL-STACK {
                key "PREFIX";
                leaf PREFIX {
                    type string; 
                } 
                leaf cisco-interop {
                    type enumeration {
                        enum cisco-interop;
                    }
                }                  //cisco-interop
            }
            list DISCOVERY_TARGETED-HELLO {
                key "PREFIX";
                leaf PREFIX {
                    type string; 
                } 
                leaf interval {
                    type enumeration {
                        enum interval;
                    }
                }                  //interval
                leaf TIME {
                    type int32;
                }                  //(1-65535)
                leaf holdtime {
                    type enumeration {
                        enum holdtime;
                    }
                }                  //holdtime
                leaf TIME_-_65535_IMPLIES {
                    type int32;
                }                  //(1-65535)
            }
            list DISCOVERY_HELLO {
                key "PREFIX";
                leaf PREFIX {
                    type string; 
                } 
                leaf interval {
                    type enumeration {
                        enum interval;
                    }
                }                  //interval
                leaf TIME {
                    type int32;
                }                  //(1-65535)
                leaf holdtime {
                    type enumeration {
                        enum holdtime;
                    }
                }                  //holdtime
                leaf TIME_-_65535_IMPLIES {
                    type int32;
                }                  //(1-65535)
            }
            list NO_DISCOVERY_TARGETED-HELLO {
                key "PREFIX";
                leaf PREFIX {
                    type string; 
                } 
                leaf interval {
                    type enumeration {
                        enum interval;
                    }
                }                  //interval
                leaf TIME {
                    type int32;
                }                  //(1-65535)
                leaf holdtime {
                    type enumeration {
                        enum holdtime;
                    }
                }                  //holdtime
                leaf TIME_-_65535_IMPLIES {
                    type int32;
                }                  //(1-65535)
            }
            list NO_DISCOVERY_HELLO {
                key "PREFIX";
                leaf PREFIX {
                    type string; 
                } 
                leaf interval {
                    type enumeration {
                        enum interval;
                    }
                }                  //interval
                leaf TIME {
                    type int32;
                }                  //(1-65535)
                leaf holdtime {
                    type enumeration {
                        enum holdtime;
                    }
                }                  //holdtime
                leaf TIME_-_65535_IMPLIES {
                    type int32;
                }                  //(1-65535)
            }
            list NO_OUTPUT_FILE {
                key "PREFIX";
                leaf PREFIX {
                    type string; 
                } 
                leaf PATH_TO_DUMP_OUTPUT {
                    type string;
                }                  //FILE
            }
            list DUAL-STACK_TRANSPORT-CONNECTION_PREFER {
                key "PREFIX";
                leaf PREFIX {
                    type string; 
                } 
                leaf ipv4 {
                    type enumeration {
                        enum ipv4;
                    }
                }                  //ipv4
            }
            list NO_DUAL-STACK_TRANSPORT-CONNECTION_PREFER {
                key "PREFIX";
                leaf PREFIX {
                    type string; 
                } 
                leaf ipv4 {
                    type enumeration {
                        enum ipv4;
                    }
                }                  //ipv4
            }
        }

    }
}
