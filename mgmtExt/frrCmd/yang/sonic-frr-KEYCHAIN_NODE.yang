module sonic-frr-KEYCHAIN_NODE {
    namespace "http://github.com/sonic-net/frr/sonic-frr-KEYCHAIN_NODE";
    prefix frr-KEYCHAIN_NODE;
    yang-version 1.1;

    import ietf-inet-types {
        prefix inet;
    }

    organization
        "SONiC";

    contact
        "SONiC";

    description
        "SONIC frr-KEYCHAIN_NODE FRR YANG";

    revision 2024-12-23 {
        description
            "Initial revision.";
    }
    container sonic-frr-KEYCHAIN_NODE {
        container KEYCHAIN_NODE {
            list OUTPUT {
                key "PREFIX";
                leaf PREFIX {
                    type string; 
                } 
                leaf file {
                    type enumeration {
                        enum file;
                    }
                }                  //file
                leaf PATH_TO_DUMP_OUTPUT {
                    type string;
                }                  //FILE
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list QUIT {
                key "PREFIX";
                leaf PREFIX {
                    type string; 
                } 
            }
            list KEY {
                key "PREFIX";
                leaf PREFIX {
                    type string; 
                } 
                leaf chain {
                    type enumeration {
                        enum chain;
                    }
                }                  //chain
                leaf KEY-CHAIN_NAME {
                    type string;
                }                  //WORD
                leaf KEY_IDENTIFIER_NUMBER {
                    type int32;
                }                  //(0-2147483647)
            }
            list EXIT {
                key "PREFIX";
                leaf PREFIX {
                    type string; 
                } 
            }
            list END {
                key "PREFIX";
                leaf PREFIX {
                    type string; 
                } 
            }
            list NO_KEY {
                key "PREFIX";
                leaf PREFIX {
                    type string; 
                } 
                leaf chain {
                    type enumeration {
                        enum chain;
                    }
                }                  //chain
                leaf KEY-CHAIN_NAME {
                    type string;
                }                  //WORD
                leaf KEY_IDENTIFIER_NUMBER {
                    type int32;
                }                  //(0-2147483647)
            }
            list NO_OUTPUT_FILE {
                key "PREFIX";
                leaf PREFIX {
                    type string; 
                } 
                leaf PATH_TO_DUMP_OUTPUT {
                    type string;
                }                  //FILE
            }
        }

    }
}
