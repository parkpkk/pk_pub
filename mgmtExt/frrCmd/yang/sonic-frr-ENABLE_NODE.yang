module sonic-frr-ENABLE_NODE {
    namespace "http://github.com/sonic-net/frr/sonic-frr-ENABLE_NODE";
    prefix frr-ENABLE_NODE;
    yang-version 1.1;

    import ietf-inet-types {
        prefix inet;
    }

    organization
        "SONiC";

    contact
        "SONiC";

    description
        "SONIC frr-ENABLE_NODE FRR YANG";

    revision 2024-12-23 {
        description
            "Initial revision.";
    }
    container sonic-frr-ENABLE_NODE {

    }
}
