module sonic-frr-BGP_NODE {
    namespace "http://github.com/sonic-net/frr/sonic-frr-BGP_NODE";
    prefix frr-BGP_NODE;
    yang-version 1.1;

    import ietf-inet-types {
        prefix inet;
    }

    organization
        "SONiC";

    contact
        "SONiC";

    description
        "SONIC frr-BGP_NODE FRR YANG";

    revision 2024-12-23 {
        description
            "Initial revision.";
    }
    container sonic-frr-BGP_NODE {
        container BGP_NODE {
            list VRF-POLICY {
                key "PREFIX";
                leaf PREFIX {
                    type string; 
                } 
                leaf VRF_NAME {
                    type string;
                }                  //NAME
            }
            list VNC {
                key "PREFIX";
                leaf PREFIX {
                    type string; 
                } 
                leaf nve-group {
                    type enumeration {
                        enum nve-group;
                    }
                }                  //nve-group
                leaf GROUP_NAME {
                    type string;
                }                  //NAME
                leaf l2-group {
                    type enumeration {
                        enum l2-group;
                    }
                }                  //l2-group
                leaf export {
                    type enumeration {
                        enum export;
                    }
                }                  //export
                leaf EXPORT_CHOICE_CASE {
                    type enumeration {
                        enum bgp;
                        enum zebra;
                    }
                }                  //<bgp|zebra> ['Export to BGP', 'Export to Zebra (experimental)']
                leaf route-map {
                    type enumeration {
                        enum route-map;
                    }
                }                  //route-map
                leaf ROUTE_MAP_NAME {
                    type string;
                }                  //NAME
                leaf mode {
                    type enumeration {
                        enum mode;
                    }
                }                  //mode
                leaf MODE_CHOICE_CASE {
                    type enumeration {
                        enum group-nve;
                        enum ce;
                        enum none;
                        enum registering-nve;
                    }
                }                  //<group-nve|ce|none|registering-nve> ['Export routes with nve-group next-hops', 'Export routes with NVE connected router next-hops', 'Disable export', 'Export routes with registering NVE as next-hop']
                leaf group-nve_group {
                    type enumeration {
                        enum group-nve_group;
                    }
                }                  //group
                leaf REDISTRIBUTE_IP {
                    type enumeration {
                        enum ipv4;
                        enum ipv6;
                    }
                }                  //<ipv4|ipv6> ['IPv4 prefixes', 'IPv6 prefixes']
                leaf prefix-list {
                    type enumeration {
                        enum prefix-list;
                    }
                }                  //prefix-list
                leaf PREFIX_LIST_NAME {
                    type string;
                }                  //NAME
                leaf group-nve_no_group {
                    type enumeration {
                        enum group-nve_no_group;
                    }
                }                  //group
                leaf defaults {
                    type enumeration {
                        enum defaults;
                    }
                }                  //defaults
            }
            list UPDATE-DELAY {
                key "PREFIX";
                leaf PREFIX {
                    type string; 
                } 
                leaf MAX_DELAY_IN_SECONDS {
                    type int32;
                }                  //(0-3600)
                leaf ESTABLISH_WAIT_IN_SECONDS {
                    type int32;
                }                  //(1-3600)
            }
            list TIMERS {
                key "PREFIX";
                leaf PREFIX {
                    type string; 
                } 
                leaf bgp {
                    type enumeration {
                        enum bgp;
                    }
                }                  //bgp
                leaf KEEPALIVE_INTERVAL {
                    type int32;
                }                  //(0-65535)
                leaf HOLDTIME {
                    type int32;
                }                  //(0-65535)
            }
            list TABLE-MAP {
                key "PREFIX";
                leaf PREFIX {
                    type string; 
                } 
                leaf NAME_OF_THE_ROUTE {
                    type string;
                }                  //WORD
            }
            list SEGMENT-ROUTING {
                key "PREFIX";
                leaf PREFIX {
                    type string; 
                } 
                leaf srv6 {
                    type enumeration {
                        enum srv6;
                    }
                }                  //srv6
            }
            list RFP {
                key "PREFIX";
                leaf PREFIX {
                    type string; 
                } 
                leaf holddown-factor {
                    type enumeration {
                        enum holddown-factor;
                    }
                }                  //holddown-factor
                leaf PERCENTAGE_OF_REGISTRATION_LIFETIME {
                    type int32;
                }                  //(0-4294967295)
                leaf full-table-download {
                    type enumeration {
                        enum full-table-download;
                    }
                }                  //full-table-download
                leaf FULL-TABLE-DOWNLOAD_RESPONSE_FILTER_TOGGLE {
                    type enumeration {
                        enum on;
                        enum off;
                    }
                }                  //<on|off> ['Enable RFP full table download', 'Disable RFP full table download']
                leaf example-config-value {
                    type enumeration {
                        enum example-config-value;
                    }
                }                  //example-config-value
                leaf VALUE_TO_DISPLAY {
                    type string;
                }                  //VALUE
            }
            list QUIT {
                key "PREFIX";
                leaf PREFIX {
                    type string; 
                } 
            }
            list NO {
                key "PREFIX";
                leaf PREFIX {
                    type string; 
                } 
                leaf vrf-policy {
                    type enumeration {
                        enum vrf-policy;
                    }
                }                  //vrf-policy
                leaf VRF_NAME {
                    type string;
                }                  //NAME
                leaf table-map {
                    type enumeration {
                        enum table-map;
                    }
                }                  //table-map
                leaf NAME_OF_THE_ROUTE {
                    type string;
                }                  //WORD
                leaf synchronization {
                    type enumeration {
                        enum synchronization;
                    }
                }                  //synchronization
                leaf rd {
                    type enumeration {
                        enum rd;
                    }
                }                  //rd
                leaf coalesce-time {
                    type enumeration {
                        enum coalesce-time;
                    }
                }                  //coalesce-time
                leaf SUBGROUP_COALESCE_TIMER_VALUE {
                    type int32;
                }                  //(0-4294967295)
                leaf auto-summary {
                    type enumeration {
                        enum auto-summary;
                    }
                }                  //auto-summary
                leaf write-quanta {
                    type enumeration {
                        enum write-quanta;
                    }
                }                  //write-quanta
                leaf NUMBER_OF_PACKETS {
                    type int32;
                }                  //(1-64)
                leaf read-quanta {
                    type enumeration {
                        enum read-quanta;
                    }
                }                  //read-quanta
            }
            list NEIGHBOR {
                key "PREFIX";
                leaf PREFIX {
                    type string; 
                } 
                leaf INTERFACE_NAME_OR_NEIGHBOR {
                    type string;
                }                  //WORD
                leaf peer-group {
                    type enumeration {
                        enum peer-group;
                    }
                }                  //peer-group
                leaf PEER-GROUP_NAME {
                    type string;
                }                  //PGNAME
                leaf interface {
                    type enumeration {
                        enum interface;
                    }
                }                  //interface
                leaf interface_remote-as {
                    type enumeration {
                        enum interface_remote-as;
                    }
                }                  //remote-as
                leaf REMOTE-AS_BGP_PEER {
                    type union {
                        type int32;
                        type enumeration {
                        enum internal;
                        enum external;
                        }
                    }
                }                  //<(1-4294967295)|internal|external> ['AS number', 'Internal BGP peer', 'External BGP peer']
                leaf interface_peer-group {
                    type enumeration {
                        enum interface_peer-group;
                    }
                }                  //peer-group
                leaf update-source {
                    type enumeration {
                        enum update-source;
                    }
                }                  //update-source
                leaf UPDATE-SOURCE_IP_ADDRESS {
                    type union {
                        type inet:ipv4-address;
                        type inet:ipv6-address;
                        type string;
                    }
                }                  //<A.B.C.D|X:X::X:X|WORD> ['IPv4 address', 'IPv6 address', 'Interface name (requires zebra to be running)']
                leaf ttl-security_hops {
                    type enumeration {
                        enum ttl-security_hops;
                    }
                }                  //hops
                leaf NUMBER_OF_HOPS_TO {
                    type int32;
                }                  //(1-254)
                leaf timers_delayopen {
                    type enumeration {
                        enum timers_delayopen;
                    }
                }                  //delayopen
                leaf DELAYOPENTIME_TIMER_INTERVAL {
                    type int32;
                }                  //(1-240)
                leaf timers_connect {
                    type enumeration {
                        enum timers_connect;
                    }
                }                  //connect
                leaf CONNECT_TIMER {
                    type int32;
                }                  //(1-65535)
                leaf timers {
                    type enumeration {
                        enum timers;
                    }
                }                  //timers
                leaf delayopen {
                    type enumeration {
                        enum delayopen;
                    }
                }                  //delayopen
                leaf connect {
                    type enumeration {
                        enum connect;
                    }
                }                  //connect
                leaf KEEPALIVE_INTERVAL {
                    type int32;
                }                  //(0-65535)
                leaf HOLDTIME {
                    type int32;
                }                  //(0-65535)
                leaf tcp-mss {
                    type enumeration {
                        enum tcp-mss;
                    }
                }                  //tcp-mss
                leaf TCP_MSS_VALUE {
                    type int32;
                }                  //(1-65535)
                leaf strict-capability-match {
                    type enumeration {
                        enum strict-capability-match;
                    }
                }                  //strict-capability-match
                leaf solo {
                    type enumeration {
                        enum solo;
                    }
                }                  //solo
                leaf shutdown {
                    type enumeration {
                        enum shutdown;
                    }
                }                  //shutdown
                leaf shutdown_rtt {
                    type enumeration {
                        enum shutdown_rtt;
                    }
                }                  //rtt
                leaf ROUND-TRIP-TIME_IN_MILLISECONDS {
                    type int32;
                }                  //(1-65535)
                leaf count {
                    type enumeration {
                        enum count;
                    }
                }                  //count
                leaf THE_NUMBER_OF_KEEPALIVES {
                    type int32;
                }                  //(1-255)
                leaf shutdown_message {
                    type enumeration {
                        enum shutdown_message;
                    }
                }                  //message
                leaf-list MESSAGE {
                    type string;
                }                  //MSG...
                leaf sender-as-path-loop-detection {
                    type enumeration {
                        enum sender-as-path-loop-detection;
                    }
                }                  //sender-as-path-loop-detection
                leaf remote-as {
                    type enumeration {
                        enum remote-as;
                    }
                }                  //remote-as
                leaf port {
                    type enumeration {
                        enum port;
                    }
                }                  //port
                leaf TCP_PORT_NUMBER {
                    type int32;
                }                  //(0-65535)
                leaf path-attribute_discard {
                    type enumeration {
                        enum path-attribute_discard;
                    }
                }                  //discard
                leaf-list ATTRIBUTE_NUMBER {
                    type int32;
                }                  //(1-255)...
                leaf password {
                    type enumeration {
                        enum password;
                    }
                }                  //password
                leaf LIST {
                    type string;
                }                  //LINE
                leaf passive {
                    type enumeration {
                        enum passive;
                    }
                }                  //passive
                leaf override-capability {
                    type enumeration {
                        enum override-capability;
                    }
                }                  //override-capability
                leaf maximum-prefix-out {
                    type enumeration {
                        enum maximum-prefix-out;
                    }
                }                  //maximum-prefix-out
                leaf MAXIMUM_NO_OF_PREFIX {
                    type int32;
                }                  //(1-4294967295)
                leaf local-role {
                    type enumeration {
                        enum local-role;
                    }
                }                  //local-role
                leaf LOCAL-ROLE_CHOICE_CASE {
                    type enumeration {
                        enum provider;
                        enum rs-server;
                        enum rs-client;
                        enum customer;
                        enum peer;
                    }
                }                  //<provider|rs-server|rs-client|customer|peer> ['Providing transit', 'Route server', 'RS client', 'Using transit', 'Public/private peering']
                leaf strict-mode {
                    type enumeration {
                        enum strict-mode;
                    }
                }                  //strict-mode
                leaf local-as {
                    type enumeration {
                        enum local-as;
                    }
                }                  //local-as
                leaf AS_NUMBER_USED_AS {
                    type int32;
                }                  //(1-4294967295)
                leaf no-prepend {
                    type enumeration {
                        enum no-prepend;
                    }
                }                  //no-prepend
                leaf no-prepend_replace-as {
                    type enumeration {
                        enum no-prepend_replace-as;
                    }
                }                  //replace-as
                leaf graceful-restart-helper {
                    type enumeration {
                        enum graceful-restart-helper;
                    }
                }                  //graceful-restart-helper
                leaf graceful-restart-disable {
                    type enumeration {
                        enum graceful-restart-disable;
                    }
                }                  //graceful-restart-disable
                leaf graceful-restart {
                    type enumeration {
                        enum graceful-restart;
                    }
                }                  //graceful-restart
                leaf extended-optional-parameters {
                    type enumeration {
                        enum extended-optional-parameters;
                    }
                }                  //extended-optional-parameters
                leaf enforce-first-as {
                    type enumeration {
                        enum enforce-first-as;
                    }
                }                  //enforce-first-as
                leaf ebgp-multihop {
                    type enumeration {
                        enum ebgp-multihop;
                    }
                }                  //ebgp-multihop
                leaf MAXIMUM_HOP_COUNT {
                    type int32;
                }                  //(1-255)
                leaf dont-capability-negotiate {
                    type enumeration {
                        enum dont-capability-negotiate;
                    }
                }                  //dont-capability-negotiate
                leaf disable-link-bw-encoding-ieee {
                    type enumeration {
                        enum disable-link-bw-encoding-ieee;
                    }
                }                  //disable-link-bw-encoding-ieee
                leaf description {
                    type enumeration {
                        enum description;
                    }
                }                  //description
                leaf capability_extended-nexthop {
                    type enumeration {
                        enum capability_extended-nexthop;
                    }
                }                  //extended-nexthop
                leaf capability_dynamic {
                    type enumeration {
                        enum capability_dynamic;
                    }
                }                  //dynamic
                leaf bfd {
                    type enumeration {
                        enum bfd;
                    }
                }                  //bfd
                leaf bfd_profile {
                    type enumeration {
                        enum bfd_profile;
                    }
                }                  //profile
                leaf BFD_PROFILE_NAME {
                    type string;
                }                  //BFDPROF
                leaf profile {
                    type enumeration {
                        enum profile;
                    }
                }                  //profile
                leaf DETECT_MULTIPLIER {
                    type int32;
                }                  //(2-255)
                leaf REQUIRED_MIN_RECEIVE_INTERVAL {
                    type int32;
                }                  //(50-60000)
                leaf DESIRED_MIN_TRANSMIT_INTERVAL {
                    type int32;
                }                  //(50-60000)
                leaf check-control-plane-failure {
                    type enumeration {
                        enum check-control-plane-failure;
                    }
                }                  //check-control-plane-failure
                leaf advertisement-interval {
                    type enumeration {
                        enum advertisement-interval;
                    }
                }                  //advertisement-interval
                leaf TIME_IN_SECONDS {
                    type int32;
                }                  //(0-600)
                leaf EBGP_PEER_USING {
                    type enumeration {
                        enum disable-connected-check;
                        enum enforce-multihop;
                    }
                }                  //<disable-connected-check|enforce-multihop> ['one-hop away EBGP peer using loopback address', 'Enforce EBGP neighbors perform multihop']
                leaf graceful-shutdown {
                    type enumeration {
                        enum graceful-shutdown;
                    }
                }                  //graceful-shutdown
                leaf aigp {
                    type enumeration {
                        enum aigp;
                    }
                }                  //aigp
                leaf interface_v6only {
                    type enumeration {
                        enum interface_v6only;
                    }
                }                  //interface_v6only
                leaf interface_v6only_remote-as {
                    type enumeration {
                        enum interface_v6only_remote-as;
                    }
                }                  //remote-as
                leaf interface_v6only_peer-group {
                    type enumeration {
                        enum interface_v6only_peer-group;
                    }
                }                  //peer-group
                leaf IP_ADDRESS {
                    type union {
                        type inet:ipv4-address;
                        type inet:ipv6-address;
                    }
                }                  //<A.B.C.D|X:X::X:X> ['Neighbor address', 'Neighbor IPv6 address']
                leaf INTERFACE_NAME {
                    type string;
                }                  //WORD
            }
            list EXIT {
                key "PREFIX";
                leaf PREFIX {
                    type string; 
                } 
            }
            list END {
                key "PREFIX";
                leaf PREFIX {
                    type string; 
                } 
            }
            list DISTANCE {
                key "PREFIX";
                leaf PREFIX {
                    type string; 
                } 
                leaf bgp {
                    type enumeration {
                        enum bgp;
                    }
                }                  //bgp
                leaf DISTANCE_FOR_ROUTES_EXTERNAL {
                    type int32;
                }                  //(1-255)
                leaf DISTANCE_FOR_ROUTES_INTERNAL {
                    type int32;
                }                  //(1-255)
                leaf DISTANCE_FOR_LOCAL_ROUTES {
                    type int32;
                }                  //(1-255)
                leaf ADMINISTRATIVE_DISTANCE {
                    type int32;
                }                  //(1-255)
                leaf IP_PREFIX {
                    type inet:ipv4-prefix;
                }                  //A.B.C.D/M
                leaf ACCESS_LIST_NAME {
                    type string;
                }                  //WORD
            }
            list COALESCE-TIME {
                key "PREFIX";
                leaf PREFIX {
                    type string; 
                } 
                leaf SUBGROUP_COALESCE_TIMER_VALUE {
                    type int32;
                }                  //(0-4294967295)
            }
            list BMP {
                key "PREFIX";
                leaf PREFIX {
                    type string; 
                } 
                leaf targets {
                    type enumeration {
                        enum targets;
                    }
                }                  //targets
                leaf NAME_OF_THE_BMP {
                    type string;
                }                  //BMP
            }
            list BGP {
                key "PREFIX";
                leaf PREFIX {
                    type string; 
                } 
                leaf tcp-keepalive {
                    type enumeration {
                        enum tcp-keepalive;
                    }
                }                  //tcp-keepalive
                leaf TCP_KEEPALIVE_IDLE_TIME {
                    type int32;
                }                  //(1-65535)
                leaf TCP_KEEPALIVE_INTERVAL {
                    type int32;
                }                  //(1-65535)
                leaf TCP_KEEPALIVE_MAXIMUM_PROBES {
                    type int32;
                }                  //(1-30)
                leaf suppress-duplicates {
                    type enumeration {
                        enum suppress-duplicates;
                    }
                }                  //suppress-duplicates
                leaf router-id {
                    type enumeration {
                        enum router-id;
                    }
                }                  //router-id
                leaf MANUALLY_CONFIGURED_ROUTER_IDENTIFIER {
                    type inet:ipv4-address;
                }                  //A.B.C.D
                leaf reject-as-sets {
                    type enumeration {
                        enum reject-as-sets;
                    }
                }                  //reject-as-sets
                leaf minimum-holdtime {
                    type enumeration {
                        enum minimum-holdtime;
                    }
                }                  //minimum-holdtime
                leaf SECONDS {
                    type int32;
                }                  //(1-65535)
                leaf log-neighbor-changes {
                    type enumeration {
                        enum log-neighbor-changes;
                    }
                }                  //log-neighbor-changes
                leaf graceful-shutdown {
                    type enumeration {
                        enum graceful-shutdown;
                    }
                }                  //graceful-shutdown
                leaf graceful-restart-disable {
                    type enumeration {
                        enum graceful-restart-disable;
                    }
                }                  //graceful-restart-disable
                leaf fast-external-failover {
                    type enumeration {
                        enum fast-external-failover;
                    }
                }                  //fast-external-failover
                leaf fast-convergence {
                    type enumeration {
                        enum fast-convergence;
                    }
                }                  //fast-convergence
                leaf ebgp-requires-policy {
                    type enumeration {
                        enum ebgp-requires-policy;
                    }
                }                  //ebgp-requires-policy
                leaf disable-ebgp-connected-route-check {
                    type enumeration {
                        enum disable-ebgp-connected-route-check;
                    }
                }                  //disable-ebgp-connected-route-check
                leaf deterministic-med {
                    type enumeration {
                        enum deterministic-med;
                    }
                }                  //deterministic-med
                leaf cluster-id {
                    type enumeration {
                        enum cluster-id;
                    }
                }                  //cluster-id
                leaf CLUSTER-ID_CHOICE_CASE {
                    type union {
                        type inet:ipv4-address;
                        type int32;
                    }
                }                  //<A.B.C.D|(1-4294967295)> ['Route-Reflector Cluster-id in IP address format', 'Route-Reflector Cluster-id as 32 bit quantity']
                leaf always-compare-med {
                    type enumeration {
                        enum always-compare-med;
                    }
                }                  //always-compare-med
                leaf suppress-fib-pending {
                    type enumeration {
                        enum suppress-fib-pending;
                    }
                }                  //suppress-fib-pending
                leaf hard-administrative-reset {
                    type enumeration {
                        enum hard-administrative-reset;
                    }
                }                  //hard-administrative-reset
                leaf allow-martian-nexthop {
                    type enumeration {
                        enum allow-martian-nexthop;
                    }
                }                  //allow-martian-nexthop
            }
            list ADDRESS-FAMILY {
                key "PREFIX";
                leaf PREFIX {
                    type string; 
                } 
                leaf evpn {
                    type enumeration {
                        enum evpn;
                    }
                }                  //evpn
            }
            list WRITE-QUANTA {
                key "PREFIX";
                leaf PREFIX {
                    type string; 
                } 
                leaf NUMBER_OF_PACKETS {
                    type int32;
                }                  //(1-64)
            }
            list READ-QUANTA {
                key "PREFIX";
                leaf PREFIX {
                    type string; 
                } 
                leaf NUMBER_OF_PACKETS {
                    type int32;
                }                  //(1-10)
            }
            list NETWORK {
                key "PREFIX";
                leaf PREFIX {
                    type string; 
                } 
                leaf IP_PREFIX {
                    type inet:ipv4-prefix;
                }                  //A.B.C.D/M
                leaf route-map {
                    type enumeration {
                        enum route-map;
                    }
                }                  //route-map
                leaf NAME_OF_THE_ROUTE {
                    type string;
                }                  //RMAP_NAME
                leaf label-index {
                    type enumeration {
                        enum label-index;
                    }
                }                  //label-index
                leaf LABEL_INDEX_VALUE {
                    type int32;
                }                  //(0-1048560)
                leaf backdoor {
                    type enumeration {
                        enum backdoor;
                    }
                }                  //backdoor
                leaf NETWORK_NUMBER {
                    type inet:ipv4-address;
                }                  //A.B.C.D
                leaf mask {
                    type enumeration {
                        enum mask;
                    }
                }                  //mask
                leaf NETWORK_MASK {
                    type inet:ipv4-address;
                }                  //A.B.C.D
            }
            list AGGREGATE-ADDRESS {
                key "PREFIX";
                leaf PREFIX {
                    type string; 
                } 
                leaf IP_PREFIX {
                    type inet:ipv4-prefix;
                }                  //A.B.C.D/M
                leaf as-set {
                    type enumeration {
                        enum as-set;
                    }
                }                  //as-set
                leaf summary-only {
                    type enumeration {
                        enum summary-only;
                    }
                }                  //summary-only
                leaf route-map {
                    type enumeration {
                        enum route-map;
                    }
                }                  //route-map
                leaf ROUTE_MAP_NAME {
                    type string;
                }                  //RMAP_NAME
                leaf origin {
                    type enumeration {
                        enum origin;
                    }
                }                  //origin
                leaf ORIGIN_CHOICE_CASE {
                    type enumeration {
                        enum egp;
                        enum igp;
                        enum incomplete;
                    }
                }                  //<egp|igp|incomplete> ['Remote EGP', 'Local IGP', 'Unknown heritage']
                leaf matching-MED-only {
                    type enumeration {
                        enum matching-MED-only;
                    }
                }                  //matching-MED-only
                leaf suppress-map {
                    type enumeration {
                        enum suppress-map;
                    }
                }                  //suppress-map
                leaf ROUTE_MAP_WITH_THE {
                    type string;
                }                  //RMAP_NAME
                leaf AGGREGATE_ADDRESS {
                    type inet:ipv4-address;
                }                  //A.B.C.D
                leaf AGGREGATE_MASK {
                    type inet:ipv4-address;
                }                  //A.B.C.D
            }
            list OUTPUT {
                key "PREFIX";
                leaf PREFIX {
                    type string; 
                } 
                leaf file {
                    type enumeration {
                        enum file;
                    }
                }                  //file
                leaf PATH_TO_DUMP_OUTPUT {
                    type string;
                }                  //FILE
            }
            list LIST {
                key "PREFIX";
                leaf PREFIX {
                    type string; 
                } 
                leaf permutations {
                    type enumeration {
                        enum permutations;
                    }
                }                  //permutations
            }
            list FIND {
                key "PREFIX";
                leaf PREFIX {
                    type string; 
                } 
                leaf-list SEARCH_PATTERN {
                    type string;
                }                  //REGEX...
            }
            list VNC_REDISTRIBUTE {
                key "PREFIX";
                leaf PREFIX {
                    type string; 
                } 
                leaf nve-group {
                    type enumeration {
                        enum nve-group;
                    }
                }                  //nve-group
                leaf GROUP_NAME {
                    type string;
                }                  //NAME
                leaf mode {
                    type enumeration {
                        enum mode;
                    }
                }                  //mode
                leaf MODE_CHOICE_CASE {
                    type enumeration {
                        enum nve-group;
                        enum plain;
                        enum resolve-nve;
                    }
                }                  //<nve-group|plain|resolve-nve> ['Based on redistribute nve-group', 'Unmodified', 'Resolve each nexthop to connected NVEs']
                leaf lifetime {
                    type enumeration {
                        enum lifetime;
                    }
                }                  //lifetime
                leaf LIFETIME_CHOICE_CASE {
                    type union {
                        type string;
                        type enumeration {
                        enum infinite;
                        }
                    }
                }                  //<LIFETIME|infinite> ['lifetime value (32 bit)', 'Allow lifetime to never expire']
                leaf REDISTRIBUTE_IP {
                    type enumeration {
                        enum ipv4;
                        enum ipv6;
                    }
                }                  //<ipv4|ipv6> ['IPv4 routes', 'IPv6 routes']
                leaf bgp-direct-to-nve-groups {
                    type enumeration {
                        enum bgp-direct-to-nve-groups;
                    }
                }                  //bgp-direct-to-nve-groups
                leaf bgp-direct-to-nve-groups_view {
                    type enumeration {
                        enum bgp-direct-to-nve-groups_view;
                    }
                }                  //view
                leaf BGP_VIEW_NAME {
                    type string;
                }                  //NAME
                leaf CHOICE_CASE {
                    type enumeration {
                        enum bgp;
                        enum bgp-direct;
                        enum connected;
                        enum kernel;
                        enum ospf;
                        enum rip;
                        enum static;
                    }
                }                  //<bgp|bgp-direct|connected|kernel|ospf|rip|static> ['From BGP', 'From BGP without Zebra', 'Connected interfaces', 'From kernel routes', 'From Open Shortest Path First (OSPF)', 'From Routing Information Protocol (RIP)', 'From Static routes']
                leaf route-map {
                    type enumeration {
                        enum route-map;
                    }
                }                  //route-map
                leaf ROUTE_MAP_NAME {
                    type string;
                }                  //NAME
                leaf prefix-list {
                    type enumeration {
                        enum prefix-list;
                    }
                }                  //prefix-list
                leaf PREFIX_LIST_NAME {
                    type string;
                }                  //NAME
            }
            list VNC_ADVERTISE-UN-METHOD {
                key "PREFIX";
                leaf PREFIX {
                    type string; 
                } 
                leaf encap-attr {
                    type enumeration {
                        enum encap-attr;
                    }
                }                  //encap-attr
            }
            list NO_VNC {
                key "PREFIX";
                leaf PREFIX {
                    type string; 
                } 
                leaf nve-group {
                    type enumeration {
                        enum nve-group;
                    }
                }                  //nve-group
                leaf GROUP_NAME {
                    type string;
                }                  //NAME
                leaf l2-group {
                    type enumeration {
                        enum l2-group;
                    }
                }                  //l2-group
                leaf export {
                    type enumeration {
                        enum export;
                    }
                }                  //export
                leaf EXPORT_CHOICE_CASE {
                    type enumeration {
                        enum bgp;
                        enum zebra;
                    }
                }                  //<bgp|zebra> ['Export to BGP', 'Export to Zebra (experimental)']
                leaf route-map {
                    type enumeration {
                        enum route-map;
                    }
                }                  //route-map
                leaf ROUTE_MAP_NAME {
                    type string;
                }                  //NAME
                leaf REDISTRIBUTE_IP {
                    type enumeration {
                        enum ipv4;
                        enum ipv6;
                    }
                }                  //<ipv4|ipv6> ['IPv4 prefixes', 'IPv6 prefixes']
                leaf prefix-list {
                    type enumeration {
                        enum prefix-list;
                    }
                }                  //prefix-list
                leaf PREFIX_LIST_NAME {
                    type string;
                }                  //NAME
            }
            list NO_UPDATE-DELAY {
                key "PREFIX";
                leaf PREFIX {
                    type string; 
                } 
                leaf MAX_DELAY_IN_SECONDS {
                    type int32;
                }                  //(0-3600)
                leaf ESTABLISH_WAIT_IN_SECONDS {
                    type int32;
                }                  //(1-3600)
            }
            list NO_SEGMENT-ROUTING {
                key "PREFIX";
                leaf PREFIX {
                    type string; 
                } 
                leaf srv6 {
                    type enumeration {
                        enum srv6;
                    }
                }                  //srv6
            }
            list NO_NEIGHBOR {
                key "PREFIX";
                leaf PREFIX {
                    type string; 
                } 
                leaf INTERFACE_NAME_OR_NEIGHBOR {
                    type string;
                }                  //WORD
                leaf remote-as {
                    type enumeration {
                        enum remote-as;
                    }
                }                  //remote-as
                leaf REMOTE-AS_BGP_PEER {
                    type union {
                        type int32;
                        type enumeration {
                        enum internal;
                        enum external;
                        }
                    }
                }                  //<(1-4294967295)|internal|external> ['AS number', 'Internal BGP peer', 'External BGP peer']
                leaf peer-group {
                    type enumeration {
                        enum peer-group;
                    }
                }                  //peer-group
                leaf PEER-GROUP_NAME {
                    type string;
                }                  //PGNAME
                leaf interface {
                    type enumeration {
                        enum interface;
                    }
                }                  //interface
                leaf interface_peer-group {
                    type enumeration {
                        enum interface_peer-group;
                    }
                }                  //peer-group
                leaf interface_remote-as {
                    type enumeration {
                        enum interface_remote-as;
                    }
                }                  //remote-as
                leaf update-source {
                    type enumeration {
                        enum update-source;
                    }
                }                  //update-source
                leaf IP_ADDRESS {
                    type union {
                        type inet:ipv4-address;
                        type inet:ipv6-address;
                        type string;
                    }
                }                  //<A.B.C.D|X:X::X:X|WORD> ['IPv4 address', 'IPv6 address', 'Interface name (requires zebra to be running)']
                leaf ttl-security_hops {
                    type enumeration {
                        enum ttl-security_hops;
                    }
                }                  //hops
                leaf NUMBER_OF_HOPS_TO {
                    type int32;
                }                  //(1-254)
                leaf timers {
                    type enumeration {
                        enum timers;
                    }
                }                  //timers
                leaf KEEPALIVE_INTERVAL {
                    type int32;
                }                  //(0-65535)
                leaf HOLDTIME {
                    type int32;
                }                  //(0-65535)
                leaf tcp-mss {
                    type enumeration {
                        enum tcp-mss;
                    }
                }                  //tcp-mss
                leaf TCP_MSS_VALUE {
                    type int32;
                }                  //(1-65535)
                leaf strict-capability-match {
                    type enumeration {
                        enum strict-capability-match;
                    }
                }                  //strict-capability-match
                leaf solo {
                    type enumeration {
                        enum solo;
                    }
                }                  //solo
                leaf shutdown {
                    type enumeration {
                        enum shutdown;
                    }
                }                  //shutdown
                leaf shutdown_message {
                    type enumeration {
                        enum shutdown_message;
                    }
                }                  //message
                leaf-list MESSAGE {
                    type string;
                }                  //MSG...
                leaf sender-as-path-loop-detection {
                    type enumeration {
                        enum sender-as-path-loop-detection;
                    }
                }                  //sender-as-path-loop-detection
                leaf port {
                    type enumeration {
                        enum port;
                    }
                }                  //port
                leaf TCP_PORT_NUMBER {
                    type int32;
                }                  //(0-65535)
                leaf password {
                    type enumeration {
                        enum password;
                    }
                }                  //password
                leaf LIST {
                    type string;
                }                  //LINE
                leaf passive {
                    type enumeration {
                        enum passive;
                    }
                }                  //passive
                leaf override-capability {
                    type enumeration {
                        enum override-capability;
                    }
                }                  //override-capability
                leaf maximum-prefix-out {
                    type enumeration {
                        enum maximum-prefix-out;
                    }
                }                  //maximum-prefix-out
                leaf MAXIMUM_NO_OF_PREFIX {
                    type int32;
                }                  //(1-4294967295)
                leaf local-role {
                    type enumeration {
                        enum local-role;
                    }
                }                  //local-role
                leaf LOCAL-ROLE_CHOICE_CASE {
                    type enumeration {
                        enum provider;
                        enum rs-server;
                        enum rs-client;
                        enum customer;
                        enum peer;
                    }
                }                  //<provider|rs-server|rs-client|customer|peer> ['Providing transit', 'Route server', 'RS client', 'Using transit', 'Public/private peering']
                leaf strict-mode {
                    type enumeration {
                        enum strict-mode;
                    }
                }                  //strict-mode
                leaf local-as {
                    type enumeration {
                        enum local-as;
                    }
                }                  //local-as
                leaf AS_NUMBER_USED_AS {
                    type int32;
                }                  //(1-4294967295)
                leaf no-prepend {
                    type enumeration {
                        enum no-prepend;
                    }
                }                  //no-prepend
                leaf no-prepend_replace-as {
                    type enumeration {
                        enum no-prepend_replace-as;
                    }
                }                  //replace-as
                leaf graceful-restart-helper {
                    type enumeration {
                        enum graceful-restart-helper;
                    }
                }                  //graceful-restart-helper
                leaf graceful-restart-disable {
                    type enumeration {
                        enum graceful-restart-disable;
                    }
                }                  //graceful-restart-disable
                leaf graceful-restart {
                    type enumeration {
                        enum graceful-restart;
                    }
                }                  //graceful-restart
                leaf extended-optional-parameters {
                    type enumeration {
                        enum extended-optional-parameters;
                    }
                }                  //extended-optional-parameters
                leaf enforce-first-as {
                    type enumeration {
                        enum enforce-first-as;
                    }
                }                  //enforce-first-as
                leaf ebgp-multihop {
                    type enumeration {
                        enum ebgp-multihop;
                    }
                }                  //ebgp-multihop
                leaf MAXIMUM_HOP_COUNT {
                    type int32;
                }                  //(1-255)
                leaf dont-capability-negotiate {
                    type enumeration {
                        enum dont-capability-negotiate;
                    }
                }                  //dont-capability-negotiate
                leaf disable-link-bw-encoding-ieee {
                    type enumeration {
                        enum disable-link-bw-encoding-ieee;
                    }
                }                  //disable-link-bw-encoding-ieee
                leaf description {
                    type enumeration {
                        enum description;
                    }
                }                  //description
                leaf capability_extended-nexthop {
                    type enumeration {
                        enum capability_extended-nexthop;
                    }
                }                  //extended-nexthop
                leaf capability_dynamic {
                    type enumeration {
                        enum capability_dynamic;
                    }
                }                  //dynamic
                leaf bfd {
                    type enumeration {
                        enum bfd;
                    }
                }                  //bfd
                leaf bfd_check-control-plane-failure {
                    type enumeration {
                        enum bfd_check-control-plane-failure;
                    }
                }                  //check-control-plane-failure
                leaf advertisement-interval {
                    type enumeration {
                        enum advertisement-interval;
                    }
                }                  //advertisement-interval
                leaf TIME_IN_SECONDS {
                    type int32;
                }                  //(0-600)
                leaf EBGP_PEER_USING {
                    type enumeration {
                        enum disable-connected-check;
                        enum enforce-multihop;
                    }
                }                  //<disable-connected-check|enforce-multihop> ['one-hop away EBGP peer using loopback address', 'Enforce EBGP neighbors perform multihop']
                leaf graceful-shutdown {
                    type enumeration {
                        enum graceful-shutdown;
                    }
                }                  //graceful-shutdown
                leaf aigp {
                    type enumeration {
                        enum aigp;
                    }
                }                  //aigp
                leaf interface_v6only {
                    type enumeration {
                        enum interface_v6only;
                    }
                }                  //interface_v6only
                leaf interface_v6only_peer-group {
                    type enumeration {
                        enum interface_v6only_peer-group;
                    }
                }                  //peer-group
                leaf interface_v6only_remote-as {
                    type enumeration {
                        enum interface_v6only_remote-as;
                    }
                }                  //remote-as
                leaf timers_delayopen {
                    type enumeration {
                        enum timers_delayopen;
                    }
                }                  //timers_delayopen
                leaf DELAYOPENTIME_TIMER_INTERVAL {
                    type int32;
                }                  //(0-65535)
                leaf timers_connect {
                    type enumeration {
                        enum timers_connect;
                    }
                }                  //timers_connect
                leaf CONNECT_TIMER {
                    type int32;
                }                  //(1-65535)
                leaf shutdown_rtt {
                    type enumeration {
                        enum shutdown_rtt;
                    }
                }                  //shutdown_rtt
                leaf ROUND-TRIP-TIME_IN_MILLISECONDS {
                    type int32;
                }                  //(1-65535)
                leaf count {
                    type enumeration {
                        enum count;
                    }
                }                  //count
                leaf THE_NUMBER_OF_KEEPALIVES {
                    type int32;
                }                  //(1-255)
                leaf path-attribute_discard {
                    type enumeration {
                        enum path-attribute_discard;
                    }
                }                  //path-attribute_discard
                leaf ATTRIBUTE_NUMBER {
                    type int32;
                }                  //(1-255)
                leaf bfd_profile {
                    type enumeration {
                        enum bfd_profile;
                    }
                }                  //bfd_profile
                leaf BFD_PROFILE_NAME {
                    type string;
                }                  //BFDPROF
                leaf INTERFACE_NAME {
                    type string;
                }                  //WORD
            }
            list NO_DISTANCE {
                key "PREFIX";
                leaf PREFIX {
                    type string; 
                } 
                leaf ADMINISTRATIVE_DISTANCE {
                    type int32;
                }                  //(1-255)
                leaf IP_PREFIX {
                    type inet:ipv4-prefix;
                }                  //A.B.C.D/M
                leaf ACCESS_LIST_NAME {
                    type string;
                }                  //WORD
            }
            list NO_BMP {
                key "PREFIX";
                leaf PREFIX {
                    type string; 
                } 
                leaf targets {
                    type enumeration {
                        enum targets;
                    }
                }                  //targets
                leaf NAME_OF_THE_BMP {
                    type string;
                }                  //BMP
            }
            list NO_BGP {
                key "PREFIX";
                leaf PREFIX {
                    type string; 
                } 
                leaf suppress-duplicates {
                    type enumeration {
                        enum suppress-duplicates;
                    }
                }                  //suppress-duplicates
                leaf reject-as-sets {
                    type enumeration {
                        enum reject-as-sets;
                    }
                }                  //reject-as-sets
                leaf log-neighbor-changes {
                    type enumeration {
                        enum log-neighbor-changes;
                    }
                }                  //log-neighbor-changes
                leaf graceful-shutdown {
                    type enumeration {
                        enum graceful-shutdown;
                    }
                }                  //graceful-shutdown
                leaf graceful-restart-disable {
                    type enumeration {
                        enum graceful-restart-disable;
                    }
                }                  //graceful-restart-disable
                leaf fast-external-failover {
                    type enumeration {
                        enum fast-external-failover;
                    }
                }                  //fast-external-failover
                leaf fast-convergence {
                    type enumeration {
                        enum fast-convergence;
                    }
                }                  //fast-convergence
                leaf ebgp-requires-policy {
                    type enumeration {
                        enum ebgp-requires-policy;
                    }
                }                  //ebgp-requires-policy
                leaf disable-ebgp-connected-route-check {
                    type enumeration {
                        enum disable-ebgp-connected-route-check;
                    }
                }                  //disable-ebgp-connected-route-check
                leaf deterministic-med {
                    type enumeration {
                        enum deterministic-med;
                    }
                }                  //deterministic-med
                leaf always-compare-med {
                    type enumeration {
                        enum always-compare-med;
                    }
                }                  //always-compare-med
                leaf suppress-fib-pending {
                    type enumeration {
                        enum suppress-fib-pending;
                    }
                }                  //suppress-fib-pending
                leaf hard-administrative-reset {
                    type enumeration {
                        enum hard-administrative-reset;
                    }
                }                  //hard-administrative-reset
                leaf allow-martian-nexthop {
                    type enumeration {
                        enum allow-martian-nexthop;
                    }
                }                  //allow-martian-nexthop
            }
            list NO_NETWORK {
                key "PREFIX";
                leaf PREFIX {
                    type string; 
                } 
                leaf IP_PREFIX {
                    type inet:ipv4-prefix;
                }                  //A.B.C.D/M
                leaf route-map {
                    type enumeration {
                        enum route-map;
                    }
                }                  //route-map
                leaf NAME_OF_THE_ROUTE {
                    type string;
                }                  //RMAP_NAME
                leaf label-index {
                    type enumeration {
                        enum label-index;
                    }
                }                  //label-index
                leaf LABEL_INDEX_VALUE {
                    type int32;
                }                  //(0-1048560)
                leaf backdoor {
                    type enumeration {
                        enum backdoor;
                    }
                }                  //backdoor
                leaf NETWORK_NUMBER {
                    type inet:ipv4-address;
                }                  //A.B.C.D
                leaf mask {
                    type enumeration {
                        enum mask;
                    }
                }                  //mask
                leaf NETWORK_MASK {
                    type inet:ipv4-address;
                }                  //A.B.C.D
            }
            list NO_AGGREGATE-ADDRESS {
                key "PREFIX";
                leaf PREFIX {
                    type string; 
                } 
                leaf IP_PREFIX {
                    type inet:ipv4-prefix;
                }                  //A.B.C.D/M
                leaf as-set {
                    type enumeration {
                        enum as-set;
                    }
                }                  //as-set
                leaf summary-only {
                    type enumeration {
                        enum summary-only;
                    }
                }                  //summary-only
                leaf route-map {
                    type enumeration {
                        enum route-map;
                    }
                }                  //route-map
                leaf ROUTE_MAP_NAME {
                    type string;
                }                  //RMAP_NAME
                leaf origin {
                    type enumeration {
                        enum origin;
                    }
                }                  //origin
                leaf ORIGIN_CHOICE_CASE {
                    type enumeration {
                        enum egp;
                        enum igp;
                        enum incomplete;
                    }
                }                  //<egp|igp|incomplete> ['Remote EGP', 'Local IGP', 'Unknown heritage']
                leaf matching-MED-only {
                    type enumeration {
                        enum matching-MED-only;
                    }
                }                  //matching-MED-only
                leaf suppress-map {
                    type enumeration {
                        enum suppress-map;
                    }
                }                  //suppress-map
                leaf ROUTE_MAP_WITH_THE {
                    type string;
                }                  //RMAP_NAME
                leaf AGGREGATE_ADDRESS {
                    type inet:ipv4-address;
                }                  //A.B.C.D
                leaf AGGREGATE_MASK {
                    type inet:ipv4-address;
                }                  //A.B.C.D
            }
            list BMP_MIRROR {
                key "PREFIX";
                leaf PREFIX {
                    type string; 
                } 
                leaf buffer-limit {
                    type enumeration {
                        enum buffer-limit;
                    }
                }                  //buffer-limit
                leaf LIMIT_IN_BYTES {
                    type int32;
                }                  //(0-4294967294)
            }
            list BGP_SHUTDOWN {
                key "PREFIX";
                leaf PREFIX {
                    type string; 
                } 
                leaf message {
                    type enumeration {
                        enum message;
                    }
                }                  //message
                leaf-list MESSAGE {
                    type string;
                }                  //MSG...
            }
            list BGP_ROUTE-REFLECTOR {
                key "PREFIX";
                leaf PREFIX {
                    type string; 
                } 
                leaf allow-outbound-policy {
                    type enumeration {
                        enum allow-outbound-policy;
                    }
                }                  //allow-outbound-policy
            }
            list BGP_ROUTE-MAP {
                key "PREFIX";
                leaf PREFIX {
                    type string; 
                } 
                leaf delay-timer {
                    type enumeration {
                        enum delay-timer;
                    }
                }                  //delay-timer
                leaf DISABLES_THE_TIMER_NO {
                    type int32;
                }                  //(0-600)
            }
            list BGP_NETWORK {
                key "PREFIX";
                leaf PREFIX {
                    type string; 
                } 
                leaf import-check {
                    type enumeration {
                        enum import-check;
                    }
                }                  //import-check
            }
            list BGP_MAX-MED {
                key "PREFIX";
                leaf PREFIX {
                    type string; 
                } 
                leaf on-startup {
                    type enumeration {
                        enum on-startup;
                    }
                }                  //on-startup
                leaf TIME_PERIOD_FOR_MAX-MED {
                    type int32;
                }                  //(5-86400)
                leaf MAX_MED_VALUE_TO {
                    type int32;
                }                  //(0-4294967295)
            }
            list BGP_LONG-LIVED-GRACEFUL-RESTART {
                key "PREFIX";
                leaf PREFIX {
                    type string; 
                } 
                leaf stale-time {
                    type enumeration {
                        enum stale-time;
                    }
                }                  //stale-time
                leaf STALE_TIME_VALUE {
                    type int32;
                }                  //(1-16777215)
            }
            list BGP_LISTEN {
                key "PREFIX";
                leaf PREFIX {
                    type string; 
                } 
                leaf range {
                    type enumeration {
                        enum range;
                    }
                }                  //range
                leaf RANGE_IP_PREFIX {
                    type union {
                        type inet:ipv4-prefix;
                        type inet:ipv6-prefix;
                    }
                }                  //<A.B.C.D/M|X:X::X:X/M> ['Neighbor address', 'IPv6 address']
                leaf peer-group {
                    type enumeration {
                        enum peer-group;
                    }
                }                  //peer-group
                leaf PEER-GROUP_NAME {
                    type string;
                }                  //PGNAME
                leaf limit {
                    type enumeration {
                        enum limit;
                    }
                }                  //limit
                leaf CONFIGURE_DYNAMIC_NEIGHBORS_LISTEN {
                    type int32;
                }                  //(1-65535)
            }
            list BGP_GRACEFUL-RESTART {
                key "PREFIX";
                leaf PREFIX {
                    type string; 
                } 
                leaf stalepath-time {
                    type enumeration {
                        enum stalepath-time;
                    }
                }                  //stalepath-time
                leaf DELAY_VALUE {
                    type int32;
                }                  //(1-4095)
                leaf select-defer-time {
                    type enumeration {
                        enum select-defer-time;
                    }
                }                  //select-defer-time
                leaf rib-stale-time {
                    type enumeration {
                        enum rib-stale-time;
                    }
                }                  //rib-stale-time
                leaf restart-time {
                    type enumeration {
                        enum restart-time;
                    }
                }                  //restart-time
                leaf preserve-fw-state {
                    type enumeration {
                        enum preserve-fw-state;
                    }
                }                  //preserve-fw-state
                leaf disable-eor {
                    type enumeration {
                        enum disable-eor;
                    }
                }                  //disable-eor
                leaf notification {
                    type enumeration {
                        enum notification;
                    }
                }                  //notification
            }
            list BGP_DEFAULT {
                key "PREFIX";
                leaf PREFIX {
                    type string; 
                } 
                leaf subgroup-pkt-queue-max {
                    type enumeration {
                        enum subgroup-pkt-queue-max;
                    }
                }                  //subgroup-pkt-queue-max
                leaf CONFIGURE_SUBGROUP_PACKET_QUEUE {
                    type int32;
                }                  //(20-100)
                leaf show-nexthop-hostname {
                    type enumeration {
                        enum show-nexthop-hostname;
                    }
                }                  //show-nexthop-hostname
                leaf show-hostname {
                    type enumeration {
                        enum show-hostname;
                    }
                }                  //show-hostname
                leaf local-preference {
                    type enumeration {
                        enum local-preference;
                    }
                }                  //local-preference
                leaf CONFIGURE_DEFAULT_LOCAL_PREFERENCE {
                    type int32;
                }                  //(0-4294967295)
                leaf shutdown {
                    type enumeration {
                        enum shutdown;
                    }
                }                  //shutdown
                leaf CHOICE_CASE {
                    type enumeration {
                        enum ipv4-unicast;
                        enum ipv4-multicast;
                        enum ipv4-vpn;
                        enum ipv4-labeled-unicast;
                        enum ipv4-flowspec;
                        enum ipv6-unicast;
                        enum ipv6-multicast;
                        enum ipv6-vpn;
                        enum ipv6-labeled-unicast;
                        enum ipv6-flowspec;
                        enum l2vpn-evpn;
                    }
                }                  //<ipv4-unicast|ipv4-multicast|ipv4-vpn|ipv4-labeled-unicast|ipv4-flowspec|ipv6-unicast|ipv6-multicast|ipv6-vpn|ipv6-labeled-unicast|ipv6-flowspec|l2vpn-evpn> ['Activate ipv4-unicast for a peer by default', 'Activate ipv4-multicast for a peer by default', 'Activate ipv4-vpn for a peer by default', 'Activate ipv4-labeled-unicast for a peer by default', 'Activate ipv4-flowspec for a peer by default', 'Activate ipv6-unicast for a peer by default', 'Activate ipv6-multicast for a peer by default', 'Activate ipv6-vpn for a peer by default', 'Activate ipv6-labeled-unicast for a peer by default', 'Activate ipv6-flowspec for a peer by default', 'Activate l2vpn-evpn for a peer by default']
            }
            list BGP_DAMPENING {
                key "PREFIX";
                leaf PREFIX {
                    type string; 
                } 
                leaf HALF-LIFE_TIME_FOR_THE {
                    type int32;
                }                  //(1-45)
                leaf VALUE_TO_START_REUSING {
                    type int32;
                }                  //(1-20000)
                leaf VALUE_TO_START_SUPPRESSING {
                    type int32;
                }                  //(1-50000)
                leaf MAXIMUM_DURATION_TO_SUPPRESS {
                    type int32;
                }                  //(1-255)
            }
            list BGP_CONFEDERATION {
                key "PREFIX";
                leaf PREFIX {
                    type string; 
                } 
                leaf peers {
                    type enumeration {
                        enum peers;
                    }
                }                  //peers
                leaf-list AS_NUMBER {
                    type int32;
                }                  //(1-4294967295)...
                leaf identifier {
                    type enumeration {
                        enum identifier;
                    }
                }                  //identifier
                leaf SET_ROUTING_DOMAIN_CONFEDERATION {
                    type int32;
                }                  //(1-4294967295)
            }
            list BGP_CLIENT-TO-CLIENT {
                key "PREFIX";
                leaf PREFIX {
                    type string; 
                } 
                leaf reflection {
                    type enumeration {
                        enum reflection;
                    }
                }                  //reflection
            }
            list BGP_BESTPATH {
                key "PREFIX";
                leaf PREFIX {
                    type string; 
                } 
                leaf compare-routerid {
                    type enumeration {
                        enum compare-routerid;
                    }
                }                  //compare-routerid
                leaf bandwidth {
                    type enumeration {
                        enum bandwidth;
                    }
                }                  //bandwidth
                leaf BANDWIDTH_CHOICE_CASE {
                    type enumeration {
                        enum ignore;
                        enum skip-missing;
                        enum default-weight-for-missing;
                    }
                }                  //<ignore|skip-missing|default-weight-for-missing> ['Ignore link bandwidth (i.e., do regular ECMP, not weighted)', 'Ignore paths without link bandwidth for ECMP (if other paths have it)', 'Assign a low default weight (value 1) to paths not having link bandwidth']
                leaf aigp {
                    type enumeration {
                        enum aigp;
                    }
                }                  //aigp
            }
            list BGP_CONDITIONAL-ADVERTISEMENT {
                key "PREFIX";
                leaf PREFIX {
                    type string; 
                } 
                leaf timer {
                    type enumeration {
                        enum timer;
                    }
                }                  //timer
                leaf PERIOD_BETWEEN_BGP_TABLE {
                    type int32;
                }                  //(5-240)
            }
            list ADDRESS-FAMILY_VPNV6 {
                key "PREFIX";
                leaf PREFIX {
                    type string; 
                } 
                leaf unicast {
                    type enumeration {
                        enum unicast;
                    }
                }                  //unicast
            }
            list ADDRESS-FAMILY_VPNV4 {
                key "PREFIX";
                leaf PREFIX {
                    type string; 
                } 
                leaf unicast {
                    type enumeration {
                        enum unicast;
                    }
                }                  //unicast
            }
            list ADDRESS-FAMILY_L2VPN {
                key "PREFIX";
                leaf PREFIX {
                    type string; 
                } 
                leaf evpn {
                    type enumeration {
                        enum evpn;
                    }
                }                  //evpn
            }
            list ADDRESS-FAMILY_IPV6 {
                key "PREFIX";
                leaf PREFIX {
                    type string; 
                } 
                leaf vpn {
                    type enumeration {
                        enum vpn;
                    }
                }                  //vpn
                leaf multicast {
                    type enumeration {
                        enum multicast;
                    }
                }                  //multicast
                leaf labeled-unicast {
                    type enumeration {
                        enum labeled-unicast;
                    }
                }                  //labeled-unicast
                leaf flowspec {
                    type enumeration {
                        enum flowspec;
                    }
                }                  //flowspec
                leaf unicast {
                    type enumeration {
                        enum unicast;
                    }
                }                  //unicast
            }
            list ADDRESS-FAMILY_IPV4 {
                key "PREFIX";
                leaf PREFIX {
                    type string; 
                } 
                leaf vpn {
                    type enumeration {
                        enum vpn;
                    }
                }                  //vpn
                leaf multicast {
                    type enumeration {
                        enum multicast;
                    }
                }                  //multicast
                leaf labeled-unicast {
                    type enumeration {
                        enum labeled-unicast;
                    }
                }                  //labeled-unicast
                leaf flowspec {
                    type enumeration {
                        enum flowspec;
                    }
                }                  //flowspec
                leaf unicast {
                    type enumeration {
                        enum unicast;
                    }
                }                  //unicast
            }
            list VNC_REDISTRIBUTE_RESOLVE-NVE {
                key "PREFIX";
                leaf PREFIX {
                    type string; 
                } 
                leaf roo-ec-local-admin {
                    type enumeration {
                        enum roo-ec-local-admin;
                    }
                }                  //roo-ec-local-admin
                leaf FIELD_VALUE {
                    type int32;
                }                  //(0-65535)
            }
            list NO_VNC_REDISTRIBUTE {
                key "PREFIX";
                leaf PREFIX {
                    type string; 
                } 
                leaf nve-group {
                    type enumeration {
                        enum nve-group;
                    }
                }                  //nve-group
                leaf REDISTRIBUTE_IP {
                    type enumeration {
                        enum ipv4;
                        enum ipv6;
                    }
                }                  //<ipv4|ipv6> ['IPv4 routes', 'IPv6 routes']
                leaf REDISTRIBUTE-IP_CHOICE_CASE {
                    type enumeration {
                        enum bgp;
                        enum bgp-direct;
                        enum bgp-direct-to-nve-groups;
                        enum connected;
                        enum kernel;
                        enum ospf;
                        enum rip;
                        enum static;
                    }
                }                  //<bgp|bgp-direct|bgp-direct-to-nve-groups|connected|kernel|ospf|rip|static> ['From BGP', 'From BGP without Zebra', 'From BGP without Zebra, only to configured NVE groups', 'Connected interfaces', 'From kernel routes', 'From Open Shortest Path First (OSPF)', 'From Routing Information Protocol (RIP)', 'From Static routes']
                leaf CHOICE_CASE {
                    type enumeration {
                        enum bgp-direct;
                        enum bgp-direct-to-nve-groups;
                    }
                }                  //<bgp-direct|bgp-direct-to-nve-groups> ['Redistribute from BGP directly', 'Redistribute from BGP without Zebra, only to configured NVE groups']
                leaf route-map {
                    type enumeration {
                        enum route-map;
                    }
                }                  //route-map
                leaf prefix-list {
                    type enumeration {
                        enum prefix-list;
                    }
                }                  //prefix-list
            }
            list NO_TIMERS_BGP {
                key "PREFIX";
                leaf PREFIX {
                    type string; 
                } 
                leaf KEEPALIVE_INTERVAL {
                    type int32;
                }                  //(0-65535)
                leaf HOLDTIME {
                    type int32;
                }                  //(0-65535)
            }
            list NO_DISTANCE_BGP {
                key "PREFIX";
                leaf PREFIX {
                    type string; 
                } 
                leaf DISTANCE_FOR_ROUTES_EXTERNAL {
                    type int32;
                }                  //(1-255)
                leaf DISTANCE_FOR_ROUTES_INTERNAL {
                    type int32;
                }                  //(1-255)
                leaf DISTANCE_FOR_LOCAL_ROUTES {
                    type int32;
                }                  //(1-255)
            }
            list NO_BGP_TCP-KEEPALIVE {
                key "PREFIX";
                leaf PREFIX {
                    type string; 
                } 
                leaf TCP_KEEPALIVE_IDLE_TIME {
                    type int32;
                }                  //(1-65535)
                leaf TCP_KEEPALIVE_INTERVAL {
                    type int32;
                }                  //(1-65535)
                leaf TCP_KEEPALIVE_MAXIMUM_PROBES {
                    type int32;
                }                  //(1-30)
            }
            list NO_BGP_SHUTDOWN {
                key "PREFIX";
                leaf PREFIX {
                    type string; 
                } 
                leaf message {
                    type enumeration {
                        enum message;
                    }
                }                  //message
                leaf-list MESSAGE {
                    type string;
                }                  //MSG...
            }
            list NO_BGP_ROUTER-ID {
                key "PREFIX";
                leaf PREFIX {
                    type string; 
                } 
                leaf MANUALLY_CONFIGURED_ROUTER_IDENTIFIER {
                    type inet:ipv4-address;
                }                  //A.B.C.D
            }
            list NO_BGP_ROUTE-REFLECTOR {
                key "PREFIX";
                leaf PREFIX {
                    type string; 
                } 
                leaf allow-outbound-policy {
                    type enumeration {
                        enum allow-outbound-policy;
                    }
                }                  //allow-outbound-policy
            }
            list NO_BGP_NETWORK {
                key "PREFIX";
                leaf PREFIX {
                    type string; 
                } 
                leaf import-check {
                    type enumeration {
                        enum import-check;
                    }
                }                  //import-check
            }
            list NO_BGP_MINIMUM-HOLDTIME {
                key "PREFIX";
                leaf PREFIX {
                    type string; 
                } 
                leaf SECONDS {
                    type int32;
                }                  //(1-65535)
            }
            list NO_BGP_LISTEN {
                key "PREFIX";
                leaf PREFIX {
                    type string; 
                } 
                leaf range {
                    type enumeration {
                        enum range;
                    }
                }                  //range
                leaf RANGE_IP_PREFIX {
                    type union {
                        type inet:ipv4-prefix;
                        type inet:ipv6-prefix;
                    }
                }                  //<A.B.C.D/M|X:X::X:X/M> ['Neighbor address', 'IPv6 address']
                leaf peer-group {
                    type enumeration {
                        enum peer-group;
                    }
                }                  //peer-group
                leaf PEER-GROUP_NAME {
                    type string;
                }                  //PGNAME
            }
            list NO_BGP_GRACEFUL-RESTART {
                key "PREFIX";
                leaf PREFIX {
                    type string; 
                } 
                leaf preserve-fw-state {
                    type enumeration {
                        enum preserve-fw-state;
                    }
                }                  //preserve-fw-state
                leaf disable-eor {
                    type enumeration {
                        enum disable-eor;
                    }
                }                  //disable-eor
                leaf notification {
                    type enumeration {
                        enum notification;
                    }
                }                  //notification
            }
            list NO_BGP_DEFAULT {
                key "PREFIX";
                leaf PREFIX {
                    type string; 
                } 
                leaf show-nexthop-hostname {
                    type enumeration {
                        enum show-nexthop-hostname;
                    }
                }                  //show-nexthop-hostname
                leaf show-hostname {
                    type enumeration {
                        enum show-hostname;
                    }
                }                  //show-hostname
                leaf shutdown {
                    type enumeration {
                        enum shutdown;
                    }
                }                  //shutdown
                leaf CHOICE_CASE {
                    type enumeration {
                        enum ipv4-unicast;
                        enum ipv4-multicast;
                        enum ipv4-vpn;
                        enum ipv4-labeled-unicast;
                        enum ipv4-flowspec;
                        enum ipv6-unicast;
                        enum ipv6-multicast;
                        enum ipv6-vpn;
                        enum ipv6-labeled-unicast;
                        enum ipv6-flowspec;
                        enum l2vpn-evpn;
                    }
                }                  //<ipv4-unicast|ipv4-multicast|ipv4-vpn|ipv4-labeled-unicast|ipv4-flowspec|ipv6-unicast|ipv6-multicast|ipv6-vpn|ipv6-labeled-unicast|ipv6-flowspec|l2vpn-evpn> ['Activate ipv4-unicast for a peer by default', 'Activate ipv4-multicast for a peer by default', 'Activate ipv4-vpn for a peer by default', 'Activate ipv4-labeled-unicast for a peer by default', 'Activate ipv4-flowspec for a peer by default', 'Activate ipv6-unicast for a peer by default', 'Activate ipv6-multicast for a peer by default', 'Activate ipv6-vpn for a peer by default', 'Activate ipv6-labeled-unicast for a peer by default', 'Activate ipv6-flowspec for a peer by default', 'Activate l2vpn-evpn for a peer by default']
            }
            list NO_BGP_DAMPENING {
                key "PREFIX";
                leaf PREFIX {
                    type string; 
                } 
                leaf HALF-LIFE_TIME_FOR_THE {
                    type int32;
                }                  //(1-45)
                leaf VALUE_TO_START_REUSING {
                    type int32;
                }                  //(1-20000)
                leaf VALUE_TO_START_SUPPRESSING {
                    type int32;
                }                  //(1-50000)
                leaf MAXIMUM_DURATION_TO_SUPPRESS {
                    type int32;
                }                  //(1-255)
            }
            list NO_BGP_CONFEDERATION {
                key "PREFIX";
                leaf PREFIX {
                    type string; 
                } 
                leaf peers {
                    type enumeration {
                        enum peers;
                    }
                }                  //peers
                leaf-list AS_NUMBER {
                    type int32;
                }                  //(1-4294967295)...
            }
            list NO_BGP_CLUSTER-ID {
                key "PREFIX";
                leaf PREFIX {
                    type string; 
                } 
                leaf CHOICE_CASE {
                    type union {
                        type inet:ipv4-address;
                        type int32;
                    }
                }                  //<A.B.C.D|(1-4294967295)> ['Route-Reflector Cluster-id in IP address format', 'Route-Reflector Cluster-id as 32 bit quantity']
            }
            list NO_BGP_CLIENT-TO-CLIENT {
                key "PREFIX";
                leaf PREFIX {
                    type string; 
                } 
                leaf reflection {
                    type enumeration {
                        enum reflection;
                    }
                }                  //reflection
            }
            list NO_BGP_BESTPATH {
                key "PREFIX";
                leaf PREFIX {
                    type string; 
                } 
                leaf compare-routerid {
                    type enumeration {
                        enum compare-routerid;
                    }
                }                  //compare-routerid
                leaf aigp {
                    type enumeration {
                        enum aigp;
                    }
                }                  //aigp
            }
            list NO_BGP_CONDITIONAL-ADVERTISEMENT {
                key "PREFIX";
                leaf PREFIX {
                    type string; 
                } 
                leaf timer {
                    type enumeration {
                        enum timer;
                    }
                }                  //timer
                leaf PERIOD_BETWEEN_BGP_TABLE {
                    type int32;
                }                  //(5-240)
            }
            list NO_OUTPUT_FILE {
                key "PREFIX";
                leaf PREFIX {
                    type string; 
                } 
                leaf PATH_TO_DUMP_OUTPUT {
                    type string;
                }                  //FILE
            }
            list BGP_MAX-MED_ADMINISTRATIVE {
                key "PREFIX";
                leaf PREFIX {
                    type string; 
                } 
                leaf MAX_MED_VALUE_TO {
                    type int32;
                }                  //(0-4294967295)
            }
            list BGP_BESTPATH_PEER-TYPE {
                key "PREFIX";
                leaf PREFIX {
                    type string; 
                } 
                leaf multipath-relax {
                    type enumeration {
                        enum multipath-relax;
                    }
                }                  //multipath-relax
            }
            list BGP_BESTPATH_AS-PATH {
                key "PREFIX";
                leaf PREFIX {
                    type string; 
                } 
                leaf ignore {
                    type enumeration {
                        enum ignore;
                    }
                }                  //ignore
                leaf confed {
                    type enumeration {
                        enum confed;
                    }
                }                  //confed
            }
            list SID_VPN_PER-VRF {
                key "PREFIX";
                leaf PREFIX {
                    type string; 
                } 
                leaf export {
                    type enumeration {
                        enum export;
                    }
                }                  //export
                leaf EXPORT_CHOICE_CASE {
                    type union {
                        type int32;
                        type enumeration {
                        enum auto;
                        }
                    }
                }                  //<(1-1048575)|auto> ['Sid allocation index', 'Automatically assign a label']
            }
            list NO_BMP_MIRROR_BUFFER-LIMIT {
                key "PREFIX";
                leaf PREFIX {
                    type string; 
                } 
                leaf LIMIT_IN_BYTES {
                    type int32;
                }                  //(0-4294967294)
            }
            list NO_BGP_ROUTE-MAP_DELAY-TIMER {
                key "PREFIX";
                leaf PREFIX {
                    type string; 
                } 
                leaf DISABLES_THE_TIMER_NO {
                    type int32;
                }                  //(0-600)
            }
            list NO_BGP_MAX-MED_ON-STARTUP {
                key "PREFIX";
                leaf PREFIX {
                    type string; 
                } 
                leaf TIME_PERIOD_FOR_MAX-MED {
                    type int32;
                }                  //(5-86400)
                leaf MAX_MED_VALUE_TO {
                    type int32;
                }                  //(0-4294967295)
            }
            list NO_BGP_MAX-MED_ADMINISTRATIVE {
                key "PREFIX";
                leaf PREFIX {
                    type string; 
                } 
                leaf MAX_MED_VALUE_TO {
                    type int32;
                }                  //(0-4294967295)
            }
            list NO_BGP_LONG-LIVED-GRACEFUL-RESTART_STALE-TIME {
                key "PREFIX";
                leaf PREFIX {
                    type string; 
                } 
                leaf STALE_TIME_VALUE {
                    type int32;
                }                  //(1-16777215)
            }
            list NO_BGP_LISTEN_LIMIT {
                key "PREFIX";
                leaf PREFIX {
                    type string; 
                } 
                leaf CONFIGURE_DYNAMIC_NEIGHBORS_LISTEN {
                    type int32;
                }                  //(1-65535)
            }
            list NO_BGP_GRACEFUL-RESTART_STALEPATH-TIME {
                key "PREFIX";
                leaf PREFIX {
                    type string; 
                } 
                leaf DELAY_VALUE {
                    type int32;
                }                  //(1-4095)
            }
            list NO_BGP_GRACEFUL-RESTART_SELECT-DEFER-TIME {
                key "PREFIX";
                leaf PREFIX {
                    type string; 
                } 
                leaf DELAY_VALUE {
                    type int32;
                }                  //(0-3600)
            }
            list NO_BGP_GRACEFUL-RESTART_RIB-STALE-TIME {
                key "PREFIX";
                leaf PREFIX {
                    type string; 
                } 
                leaf DELAY_VALUE {
                    type int32;
                }                  //(1-3600)
            }
            list NO_BGP_GRACEFUL-RESTART_RESTART-TIME {
                key "PREFIX";
                leaf PREFIX {
                    type string; 
                } 
                leaf DELAY_VALUE {
                    type int32;
                }                  //(0-4095)
            }
            list NO_BGP_DEFAULT_SUBGROUP-PKT-QUEUE-MAX {
                key "PREFIX";
                leaf PREFIX {
                    type string; 
                } 
                leaf CONFIGURE_SUBGROUP_PACKET_QUEUE {
                    type int32;
                }                  //(20-100)
            }
            list NO_BGP_DEFAULT_LOCAL-PREFERENCE {
                key "PREFIX";
                leaf PREFIX {
                    type string; 
                } 
                leaf CONFIGURE_DEFAULT_LOCAL_PREFERENCE {
                    type int32;
                }                  //(0-4294967295)
            }
            list NO_BGP_CONFEDERATION_IDENTIFIER {
                key "PREFIX";
                leaf PREFIX {
                    type string; 
                } 
                leaf SET_ROUTING_DOMAIN_CONFEDERATION {
                    type int32;
                }                  //(1-4294967295)
            }
            list NO_BGP_BESTPATH_PEER-TYPE {
                key "PREFIX";
                leaf PREFIX {
                    type string; 
                } 
                leaf multipath-relax {
                    type enumeration {
                        enum multipath-relax;
                    }
                }                  //multipath-relax
            }
            list NO_BGP_BESTPATH_BANDWIDTH {
                key "PREFIX";
                leaf PREFIX {
                    type string; 
                } 
                leaf CHOICE_CASE {
                    type enumeration {
                        enum ignore;
                        enum skip-missing;
                        enum default-weight-for-missing;
                    }
                }                  //<ignore|skip-missing|default-weight-for-missing> ['Ignore link bandwidth (i.e., do regular ECMP, not weighted)', 'Ignore paths without link bandwidth for ECMP (if other paths have it)', 'Assign a low default weight (value 1) to paths not having link bandwidth']
            }
            list NO_BGP_BESTPATH_AS-PATH {
                key "PREFIX";
                leaf PREFIX {
                    type string; 
                } 
                leaf ignore {
                    type enumeration {
                        enum ignore;
                    }
                }                  //ignore
                leaf confed {
                    type enumeration {
                        enum confed;
                    }
                }                  //confed
            }
            list BGP_BESTPATH_MED_CONFED {
                key "PREFIX";
                leaf PREFIX {
                    type string; 
                } 
                leaf missing-as-worst {
                    type enumeration {
                        enum missing-as-worst;
                    }
                }                  //missing-as-worst
            }
            list BGP_BESTPATH_MED_MISSING-AS-WORST {
                key "PREFIX";
                leaf PREFIX {
                    type string; 
                } 
                leaf confed {
                    type enumeration {
                        enum confed;
                    }
                }                  //confed
            }
            list BGP_BESTPATH_AS-PATH_MULTIPATH-RELAX {
                key "PREFIX";
                leaf PREFIX {
                    type string; 
                } 
                leaf AS_SET_MODE {
                    type enumeration {
                        enum as-set;
                        enum no-as-set;
                    }
                }                  //<as-set|no-as-set> ['Generate an AS_SET', 'Do not generate an AS_SET']
            }
            list NO_SID_VPN_PER-VRF_EXPORT {
                key "PREFIX";
                leaf PREFIX {
                    type string; 
                } 
                leaf CHOICE_CASE {
                    type union {
                        type int32;
                        type enumeration {
                        enum auto;
                        }
                    }
                }                  //<(1-1048575)|auto> ['Sid allocation index', 'Automatically assign a label']
            }
            list NO_BGP_BESTPATH_MED_CONFED {
                key "PREFIX";
                leaf PREFIX {
                    type string; 
                } 
                leaf missing-as-worst {
                    type enumeration {
                        enum missing-as-worst;
                    }
                }                  //missing-as-worst
            }
            list NO_BGP_BESTPATH_MED_MISSING-AS-WORST {
                key "PREFIX";
                leaf PREFIX {
                    type string; 
                } 
                leaf confed {
                    type enumeration {
                        enum confed;
                    }
                }                  //confed
            }
            list NO_BGP_BESTPATH_AS-PATH_MULTIPATH-RELAX {
                key "PREFIX";
                leaf PREFIX {
                    type string; 
                } 
                leaf AS_SET_MODE {
                    type enumeration {
                        enum as-set;
                        enum no-as-set;
                    }
                }                  //<as-set|no-as-set> ['Generate an AS_SET', 'Do not generate an AS_SET']
            }
        }

    }
}
