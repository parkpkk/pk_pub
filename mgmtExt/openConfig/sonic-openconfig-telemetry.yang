module sonic-openconfig-telemetry {
    namespace "http://github.com/sonic-net/openconfig/sonic-openconfig-telemetry";
    prefix sonic-openconfig-telemetry;
    yang-version 1.1;

    import ietf-inet-types {
        prefix inet;
    }

    organization
        "SONiC";

    contact
        "SONiC";

    description
        "SONIC OPENCONFIG YANG AUTO CONVERTION FOR OPENCONFIG-TELEMETRY";

    revision 2026-05-05 {
        description
            "Initial revision generated by YangIntegratedStandardizer.";
    }

    container sonic-openconfig-telemetry {
        container SENSOR-GROUPS {
            list SENSOR-GROUP {
                key "sensor-group-id";
                leaf sensor-group-id {
                    type string;
                }
            }
        }
        container SENSOR-GROUP_SENSOR-PATHS {
            list SENSOR-PATH {
                key "path";
                leaf path {
                    type string;
                }
                leaf exclude-filter {
                    type string;
                }
            }
        }
        container DESTINATION-GROUPS {
            list DESTINATION-GROUP {
                key "group-id";
                leaf group-id {
                    type string;
                }
            }
        }
        container DESTINATION-GROUP_DESTINATIONS {
            list DESTINATION {
                key "destination-address destination-port";
                leaf destination-address {
                    type union {
                        type ipv4-address;
                        type ipv6-address;
                    }
                }
                leaf destination-port {
                    type uint16;
                }
            }
        }
        container PERSISTENT-SUBSCRIPTIONS {
            list PERSISTENT-SUBSCRIPTION {
                key "name";
                leaf name {
                    type string;
                }
                leaf local-source-address {
                    type union {
                        type ipv4-address;
                        type ipv6-address;
                    }
                }
                leaf originated-qos-marking {
                    type uint32 {
                        range "0..63";
                    }
                }
                leaf protocol {
                    type enumeration {
                        enum "STREAM_SSH";
                        enum "STREAM_GRPC";
                        enum "STREAM_JSON_RPC";
                        enum "STREAM_THRIFT_RPC";
                        enum "STREAM_WEBSOCKET_RPC";
                    }
                }
                leaf encoding {
                    type enumeration {
                        enum "ENC_XML";
                        enum "ENC_JSON_IETF";
                        enum "ENC_PROTO3";
                    }
                }
                leaf id {
                    type string;
                }
            }
        }
        container PERSISTENT-SUBSCRIPTION_SENSOR-PROFILES {
            list SENSOR-PROFILE {
                key "sensor-group";
                leaf sensor-group {
                    type string;
                }
                leaf sample-interval {
                    type uint64;
                }
                leaf heartbeat-interval {
                    type uint64;
                }
                leaf suppress-redundant {
                    type boolean;
                }
            }
        }
        container PERSISTENT-SUBSCRIPTION_DESTINATION-GROUPS {
            list DESTINATION-GROUP {
                key "group-id";
                leaf group-id {
                    type string;
                }
            }
        }
        container DYNAMIC-SUBSCRIPTIONS {
            list DYNAMIC-SUBSCRIPTION {
                key "id";
                leaf id {
                    type string;
                }
                leaf destination-address {
                    type union {
                        type ipv4-address;
                        type ipv6-address;
                    }
                }
                leaf destination-port {
                    type uint16;
                }
                leaf sample-interval {
                    type uint64;
                }
                leaf heartbeat-interval {
                    type uint64;
                }
                leaf suppress-redundant {
                    type boolean;
                }
                leaf originated-qos-marking {
                    type uint32 {
                        range "0..63";
                    }
                }
                leaf protocol {
                    type enumeration {
                        enum "STREAM_SSH";
                        enum "STREAM_GRPC";
                        enum "STREAM_JSON_RPC";
                        enum "STREAM_THRIFT_RPC";
                        enum "STREAM_WEBSOCKET_RPC";
                    }
                }
                leaf encoding {
                    type enumeration {
                        enum "ENC_XML";
                        enum "ENC_JSON_IETF";
                        enum "ENC_PROTO3";
                    }
                }
            }
        }
        container DYNAMIC-SUBSCRIPTION_SENSOR-PATHS {
            list SENSOR-PATH {
                key "path";
                leaf path {
                    type string;
                }
                leaf exclude-filter {
                    type string;
                }
            }
        }
    }

}
