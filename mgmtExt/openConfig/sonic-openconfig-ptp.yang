module sonic-openconfig-ptp {
    namespace "http://github.com/sonic-net/openconfig/sonic-openconfig-ptp";
    prefix sonic-openconfig-ptp;
    yang-version 1.1;

    import ietf-inet-types {
        prefix inet;
    }

    organization
        "SONiC";

    contact
        "SONiC";

    description
        "SONIC OPENCONFIG YANG AUTO CONVERTION FOR OPENCONFIG-PTP";

    revision 2026-05-05 {
        description
            "Initial revision generated by YangIntegratedStandardizer.";
    }

    container sonic-openconfig-ptp {
        container INSTANCES {
            list INSTANCE {
                key "id";
                leaf id {
                    type string;
                }
                leaf steps-removed {
                    type uint16;
                }
                leaf offset-from-master {
                    type int64;
                }
                leaf current-utc-offset {
                    type int16;
                }
                leaf current-utc-offset-valid {
                    type boolean;
                }
                leaf leap59 {
                    type boolean;
                }
                leaf leap61 {
                    type boolean;
                }
                leaf time-traceable {
                    type boolean;
                }
                leaf frequency-traceable {
                    type boolean;
                }
                leaf ptp-timescale {
                    type boolean;
                }
                leaf time-source {
                    type enumeration {
                        enum "string";
                    }
                }
                leaf clock-class {
                    type enumeration {
                        enum "string";
                    }
                }
                leaf clock-accuracy {
                    type enumeration {
                        enum "string";
                    }
                }
                leaf offset-scaled-log-variance {
                    type uint16;
                }
                leaf priority1 {
                    type uint8;
                }
                leaf priority2 {
                    type uint8;
                }
                leaf domain-number {
                    type uint8;
                }
                leaf slave-only {
                    type boolean;
                }
                leaf instance-type {
                    type enumeration {
                        enum "OC";
                        enum "BC";
                        enum "P2P_TC";
                        enum "E2E_TC";
                    }
                }
                leaf sdo-id {
                    type uint32 {
                        range "0..4095";
                    }
                }
                leaf network-transport {
                    type enumeration {
                        enum "L2";
                        enum "UDPV4";
                        enum "UDPV6";
                    }
                }
                leaf unicast-multicast {
                    type enumeration {
                        enum "UNICAST";
                        enum "MULTICAST";
                    }
                }
                leaf domain-profile {
                    type enumeration {
                        enum "IEEE1588";
                        enum "G8275.1";
                        enum "G8275.2";
                    }
                }
                leaf two-step-flag {
                    type boolean;
                }
                leaf clock-identity {
                    type string;
                }
                leaf number-ports {
                    type uint16;
                }
                leaf port-number {
                    type uint16;
                }
                leaf parent-stats {
                    type boolean;
                }
                leaf observed-parent-offset-scaled-log-variance {
                    type uint16;
                }
                leaf observed-parent-clock-phase-change-rate {
                    type int32;
                }
                leaf grandmaster-identity {
                    type string;
                }
                leaf grandmaster-priority1 {
                    type uint8;
                }
                leaf grandmaster-priority2 {
                    type uint8;
                }
            }
        }
        container INSTANCE_PORTS {
            list PORT {
                key "port-index";
                leaf port-index {
                    type string;
                }
                leaf underlying-interface {
                    type string;
                }
                leaf log-announce-interval {
                    type int8;
                }
                leaf announce-receipt-timeout {
                    type uint8;
                }
                leaf log-sync-interval {
                    type int8;
                }
                leaf delay-mechanism {
                    type enumeration {
                        enum "E2E";
                        enum "P2P";
                        enum "DISABLED";
                    }
                }
                leaf log-min-pdelay-req-interval {
                    type int8;
                }
                leaf version-number {
                    type uint8;
                }
                leaf log-min-delay-req-interval {
                    type int8;
                }
                leaf unicast-multicast {
                    type enumeration {
                        enum "UNICAST";
                        enum "MULTICAST";
                    }
                }
                leaf port-state {
                    type enumeration {
                        enum "INITIALIZING";
                        enum "FAULTY";
                        enum "DISABLED";
                        enum "LISTENING";
                        enum "PRE_MASTER";
                        enum "MASTER";
                        enum "PASSIVE";
                        enum "UNCALIBRATED";
                        enum "SLAVE";
                    }
                }
                leaf peer-mean-path-delay {
                    type int64;
                }
            }
        }
        container COMMON_SETTINGS {
            leaf delay-mechanism {
                type enumeration {
                    enum "E2E";
                    enum "P2P";
                    enum "DISABLED";
                }
            }
            leaf primary-domain {
                type uint8;
            }
            leaf two-step-flag {
                type boolean;
            }
            leaf clock-identity {
                type string;
            }
            leaf number-ports {
                type uint16;
            }
        }
        container TRANSPARENT-CLOCK-PORTS {
            list PORT {
                key "port-index";
                leaf port-index {
                    type string;
                }
                leaf underlying-interface {
                    type string;
                }
                leaf log-min-pdelay-req-interval {
                    type int8;
                }
                leaf faulty-flag {
                    type boolean;
                }
                leaf network-transport {
                    type enumeration {
                        enum "L2";
                        enum "UDPV4";
                        enum "UDPV6";
                    }
                }
                leaf clock-identity {
                    type string;
                }
                leaf port-number {
                    type uint16;
                }
                leaf peer-mean-path-delay {
                    type int64;
                }
            }
        }
    }

}
