module sonic-openconfig-lldp {
    namespace "http://github.com/sonic-net/openconfig/sonic-openconfig-lldp";
    prefix sonic-openconfig-lldp;
    yang-version 1.1;

    import ietf-inet-types {
        prefix inet;
    }

    organization
        "SONiC";

    contact
        "SONiC";

    description
        "SONIC OPENCONFIG YANG AUTO CONVERTION FOR OPENCONFIG-LLDP";

    revision 2026-05-05 {
        description
            "Initial revision generated by YangIntegratedStandardizer.";
    }

    container sonic-openconfig-lldp {
        container COMMON_SETTINGS {
            leaf enabled {
                type boolean;
            }
            leaf hello-timer {
                type uint64;
            }
            leaf system-name {
                type string;
            }
            leaf system-description {
                type string;
            }
            leaf chassis-id {
                type string;
            }
            leaf chassis-id-type {
                type enumeration {
                    enum "CHASSIS_COMPONENT";
                    enum "INTERFACE_ALIAS";
                    enum "PORT_COMPONENT";
                    enum "MAC_ADDRESS";
                    enum "NETWORK_ADDRESS";
                    enum "INTERFACE_NAME";
                    enum "LOCAL";
                }
            }
            leaf management-interface {
                type string;
            }
            leaf frame-in {
                type uint64;
            }
            leaf frame-out {
                type uint64;
            }
            leaf frame-error-in {
                type uint64;
            }
            leaf frame-discard {
                type uint64;
            }
            leaf tlv-discard {
                type uint64;
            }
            leaf tlv-unknown {
                type uint64;
            }
            leaf last-clear {
                type string;
            }
            leaf tlv-accepted {
                type uint64;
            }
            leaf entries-aged-out {
                type uint64;
            }
        }
        container MGMT-ADDRESSES {
            list MGMT-ADDRESS {
                key "address";
                leaf address {
                    type inet:ipv4-address-no-zone;
                }
                leaf interface-number {
                    type uint32;
                }
                leaf interface-number-subtype {
                    type enumeration {
                        enum "UNKNOWN";
                        enum "IFINDEX";
                        enum "SYSTEM_PORT_NUMBER";
                    }
                }
            }
        }
        container INTERFACES {
            list INTERFACE {
                key "name";
                leaf name {
                    type string;
                }
                leaf enabled {
                    type boolean;
                }
                leaf frame-in {
                    type uint64;
                }
                leaf frame-out {
                    type uint64;
                }
                leaf frame-error-in {
                    type uint64;
                }
                leaf frame-discard {
                    type uint64;
                }
                leaf tlv-discard {
                    type uint64;
                }
                leaf tlv-unknown {
                    type uint64;
                }
                leaf last-clear {
                    type string;
                }
                leaf frame-error-out {
                    type uint64;
                }
            }
        }
        container INTERFACE_NEIGHBORS {
            list NEIGHBOR {
                key "id";
                leaf id {
                    type string;
                }
                leaf system-name {
                    type string;
                }
                leaf system-description {
                    type string;
                }
                leaf chassis-id {
                    type string;
                }
                leaf chassis-id-type {
                    type enumeration {
                        enum "CHASSIS_COMPONENT";
                        enum "INTERFACE_ALIAS";
                        enum "PORT_COMPONENT";
                        enum "MAC_ADDRESS";
                        enum "NETWORK_ADDRESS";
                        enum "INTERFACE_NAME";
                        enum "LOCAL";
                    }
                }
                leaf management-interface {
                    type string;
                }
                leaf age {
                    type uint16;
                }
                leaf last-update {
                    type int64;
                }
                leaf ttl {
                    type uint16;
                }
                leaf port-id {
                    type string;
                }
                leaf port-id-type {
                    type enumeration {
                        enum "INTERFACE_ALIAS";
                        enum "PORT_COMPONENT";
                        enum "MAC_ADDRESS";
                        enum "NETWORK_ADDRESS";
                        enum "INTERFACE_NAME";
                        enum "AGENT_CIRCUIT_ID";
                        enum "LOCAL";
                    }
                }
                leaf port-description {
                    type string;
                }
            }
        }
        container INTERFACE_NEIGHBOR_MGMT-ADDRESSES {
            list MGMT-ADDRESS {
                key "address";
                leaf address {
                    type inet:ipv4-address-no-zone;
                }
                leaf interface-number {
                    type uint32;
                }
                leaf interface-number-subtype {
                    type enumeration {
                        enum "UNKNOWN";
                        enum "IFINDEX";
                        enum "SYSTEM_PORT_NUMBER";
                    }
                }
            }
        }
        container INTERFACE_NEIGHBOR_CUSTOM-TLVS {
            list TLV {
                key "type oui oui-subtype";
                leaf type {
                    type enumeration {
                        enum "NORMAL";
                        enum "STUB";
                        enum "NSSA";
                    }
                }
                leaf oui {
                    type string;
                }
                leaf oui-subtype {
                    type string;
                }
                leaf value {
                    type binary;
                }
            }
        }
        container INTERFACE_NEIGHBOR_CAPABILITIES {
            list CAPABILITY {
                key "name";
                leaf name {
                    type string;
                }
                leaf enabled {
                    type boolean;
                }
            }
        }
    }

}
