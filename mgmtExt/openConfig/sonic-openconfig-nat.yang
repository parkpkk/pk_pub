module sonic-openconfig-nat {
    namespace "http://github.com/sonic-net/openconfig/sonic-openconfig-nat";
    prefix sonic-openconfig-nat;
    yang-version 1.1;

    import ietf-inet-types {
        prefix inet;
    }

    organization
        "SONiC";

    contact
        "SONiC";

    description
        "SONIC OPENCONFIG YANG AUTO CONVERTION FOR OPENCONFIG-NAT";

    revision 2026-05-05 {
        description
            "Initial revision generated by YangIntegratedStandardizer.";
    }

    container sonic-openconfig-nat {
        container COMMON_SETTINGS {
            leaf translation-timeout {
                type uint32;
            }
            leaf max-translations {
                type uint64;
            }
            leaf log-level {
                type enumeration {
                    enum "NONE";
                    enum "ERROR";
                    enum "INFO";
                    enum "DEBUG";
                }
            }
            leaf memory-usage {
                type uint32;
            }
            leaf total-instances {
                type uint32;
            }
            leaf active-instances {
                type uint32;
            }
            leaf total-active-translations {
                type uint64;
            }
            leaf total-translation-failures {
                type uint64;
            }
        }
        container INSTANCES {
            list INSTANCE {
                key "name";
                leaf name {
                    type string;
                }
                leaf type {
                    type enumeration {
                        enum "NORMAL";
                        enum "STUB";
                        enum "NSSA";
                    }
                }
                leaf address-family {
                    type enumeration {
                        enum "IPV4_UNICAST";
                    }
                }
                leaf description {
                    type string;
                }
                leaf active-mappings {
                    type uint64;
                }
                leaf total-mappings {
                    type uint64;
                }
                leaf mapping-failures {
                    type uint64;
                }
            }
        }
        container INSTANCE_INTERFACES {
            list INTERFACE {
                key "interface";
                leaf interface { type string; }
                leaf type {
                    type enumeration {
                        enum "INSIDE";
                        enum "OUTSIDE";
                    }
                }
                leaf packets-translated {
                    type uint64;
                }
                leaf bytes-translated {
                    type uint64;
                }
                leaf translation-errors {
                    type uint64;
                }
            }
        }
        container INSTANCE_DYNAMIC {
            list POOL {
                key "name";
                leaf name {
                    type string;
                }
                leaf start-address {
                    type union {
                        type ipv4-address;
                        type ipv6-address;
                    }
                }
                leaf end-address {
                    type union {
                        type ipv4-address;
                        type ipv6-address;
                    }
                }
                leaf prefix-length {
                    type uint32 {
                        range "0..32";
                    }
                }
                leaf port-range-start {
                    type uint16;
                }
                leaf port-range-end {
                    type uint16;
                }
                leaf port-block-size {
                    type uint16;
                }
                leaf acl-set {
                    type string;
                }
                leaf max-translations {
                    type uint64;
                }
                leaf address-only {
                    type boolean;
                }
                leaf timeout {
                    type uint64;
                }
                leaf tcp-timeout {
                    type uint32;
                }
                leaf udp-timeout {
                    type uint32;
                }
                leaf icmp-timeout {
                    type uint32;
                }
                leaf overload {
                    type boolean;
                }
                leaf log-translations {
                    type boolean;
                }
                leaf max-translations-per-address {
                    type uint32;
                }
                leaf allocated-addresses {
                    type uint32;
                }
                leaf available-addresses {
                    type uint32;
                }
                leaf active-translations {
                    type uint64;
                }
                leaf acl-hit-count {
                    type uint64;
                }
            }
        }
        container INSTANCE_STATIC {
            list MAPPING {
                key "name";
                leaf name {
                    type string;
                }
                leaf type {
                    type enumeration {
                        enum "NORMAL";
                        enum "STUB";
                        enum "NSSA";
                    }
                }
                leaf internal-address {
                    type union {
                        type ipv4-address;
                        type ipv6-address;
                    }
                }
                leaf external-address {
                    type union {
                        type ipv4-address;
                        type ipv6-address;
                    }
                }
                leaf internal-port {
                    type uint16;
                }
                leaf external-port {
                    type uint16;
                }
                leaf protocol {
                    type enumeration {
                        enum "TCP";
                        enum "UDP";
                        enum "ICMP";
                        enum "ALL";
                    }
                }
                leaf acl-set {
                    type string;
                }
                leaf max-translations {
                    type uint64;
                }
                leaf creation-time {
                    type string;
                }
                leaf last-used {
                    type string;
                }
                leaf active-translations {
                    type uint64;
                }
                leaf packet-count {
                    type uint64;
                }
                leaf byte-count {
                    type uint64;
                }
                leaf acl-hit-count {
                    type uint64;
                }
            }
        }
        container INSTANCE_TRANSLATIONS {
            list TRANSLATION {
                key "translation-id";
                leaf translation-id {
                    type uint64;
                }
                leaf internal-address {
                    type union {
                        type ipv4-address;
                        type ipv6-address;
                    }
                }
                leaf internal-port {
                    type uint16;
                }
                leaf external-address {
                    type union {
                        type ipv4-address;
                        type ipv6-address;
                    }
                }
                leaf external-port {
                    type uint16;
                }
                leaf protocol {
                    type enumeration {
                        enum "TCP";
                        enum "UDP";
                        enum "ICMP";
                        enum "ALL";
                    }
                }
                leaf creation-time {
                    type string;
                }
                leaf last-activity {
                    type string;
                }
                leaf timeout {
                    type uint64;
                }
                leaf source-pool {
                    type string;
                }
                leaf source-mapping {
                    type string;
                }
                leaf packet-count-inbound {
                    type uint64;
                }
                leaf packet-count-outbound {
                    type uint64;
                }
                leaf byte-count-inbound {
                    type uint64;
                }
                leaf byte-count-outbound {
                    type uint64;
                }
            }
        }
    }

}
