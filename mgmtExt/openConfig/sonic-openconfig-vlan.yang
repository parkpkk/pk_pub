module sonic-openconfig-vlan {
    namespace "http://github.com/sonic-net/openconfig/sonic-openconfig-vlan";
    prefix sonic-openconfig-vlan;
    yang-version 1.1;

    import ietf-inet-types {
        prefix inet;
    }

    organization
        "SONiC";

    contact
        "SONiC";

    description
        "SONIC OPENCONFIG YANG AUTO CONVERTION FOR OPENCONFIG-VLAN";

    revision 2026-05-05 {
        description
            "Initial revision generated by YangIntegratedStandardizer.";
    }

    container sonic-openconfig-vlan {
        container COMMON_SETTINGS {
            leaf vlan-id {
                type uint32 {
                    range "1..4094";
                }
            }
            leaf low-vlan-id {
                type uint32 {
                    range "1..4094";
                }
            }
            leaf high-vlan-id {
                type uint32 {
                    range "1..4094";
                }
            }
            leaf inner-vlan-id {
                type uint32 {
                    range "1..4094";
                }
            }
            leaf outer-vlan-id {
                type uint32 {
                    range "1..4094";
                }
            }
            leaf inner-low-vlan-id {
                type uint32 {
                    range "1..4094";
                }
            }
            leaf inner-high-vlan-id {
                type uint32 {
                    range "1..4094";
                }
            }
            leaf outer-low-vlan-id {
                type uint32 {
                    range "1..4094";
                }
            }
            leaf outer-high-vlan-id {
                type uint32 {
                    range "1..4094";
                }
            }
            leaf vlan-stack-action {
                type enumeration {
                    enum "PUSH";
                    enum "POP";
                    enum "SWAP";
                }
            }
            leaf tpid {
                type string;
            }
            leaf interface-mode {
                type enumeration {
                    enum "ACCESS";
                    enum "TRUNK";
                }
            }
            leaf native-vlan {
                type uint32 {
                    range "1..4094";
                }
            }
            leaf access-vlan {
                type uint32 {
                    range "1..4094";
                }
            }
            leaf vlan {
                type string;
            }
        }
    }

}
