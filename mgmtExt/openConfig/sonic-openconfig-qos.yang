module sonic-openconfig-qos {
    namespace "http://github.com/sonic-net/openconfig/sonic-openconfig-qos";
    prefix sonic-openconfig-qos;
    yang-version 1.1;

    import ietf-inet-types {
        prefix inet;
    }

    organization
        "SONiC";

    contact
        "SONiC";

    description
        "SONIC OPENCONFIG YANG AUTO CONVERTION FOR OPENCONFIG-QOS";

    revision 2026-05-05 {
        description
            "Initial revision generated by YangIntegratedStandardizer.";
    }

    container sonic-openconfig-qos {
        container INTERFACES {
            list INTERFACE {
                key "interface-id";
                leaf interface-id {
                    type uint32;
                }
                leaf subinterface {
                    type uint64;
                }
                leaf buffer-allocation-profile {
                    type string;
                }
                leaf multicast-buffer-allocation-profile {
                    type string;
                }
                leaf unicast-buffer-allocation-profile {
                    type string;
                }
                leaf name {
                    type string;
                }
            }
        }
        container INTERFACE_INPUT_CLASSIFIERS {
            list CLASSIFIER {
                key "name";
                leaf type {
                    type enumeration {
                        enum "NORMAL";
                        enum "STUB";
                        enum "NSSA";
                    }
                }
                leaf name {
                    type string;
                }
            }
        }
        container INTERFACE_INPUT_CLASSIFIER_TERMS {
            list TERM {
                key "id";
                leaf id {
                    type string;
                }
                leaf matched-packets {
                    type uint64;
                }
                leaf matched-octets {
                    type uint64;
                }
            }
        }
        container INTERFACE_INPUT_QUEUES {
            list QUEUE {
                key "name";
                leaf name {
                    type string;
                }
                leaf queue-management-profile {
                    type string;
                }
                leaf max-queue-len {
                    type uint64;
                }
                leaf avg-queue-len {
                    type uint64;
                }
                leaf transmit-pkts {
                    type uint64;
                }
                leaf transmit-octets {
                    type uint64;
                }
                leaf dropped-pkts {
                    type uint64;
                }
                leaf dropped-octets {
                    type uint64;
                }
                leaf ecn-marked-pkts {
                    type uint64;
                }
                leaf ecn-marked-octets {
                    type uint64;
                }
                leaf ecn-selected-pkts {
                    type uint64;
                }
                leaf ecn-selected-octets {
                    type uint64;
                }
            }
        }
        container INTERFACE_INPUT_SCHEDULER-POLICY_SCHEDULERS {
            list SCHEDULER {
                key "sequence";
                leaf sequence {
                    type string;
                }
                leaf conforming-pkts {
                    type uint64;
                }
                leaf conforming-octets {
                    type uint64;
                }
                leaf exceeding-pkts {
                    type uint64;
                }
                leaf exceeding-octets {
                    type uint64;
                }
                leaf violating-pkts {
                    type uint64;
                }
                leaf violating-octets {
                    type uint64;
                }
            }
        }
        container INTERFACE_INPUT_VIRTUAL-OUTPUT-QUEUES {
            list VOQ-INTERFACE {
                key "name";
                leaf name {
                    type string;
                }
            }
        }
        container INTERFACE_INPUT_VIRTUAL-OUTPUT-QUEUES_VOQ-INTERFACE_QUEUES {
            list QUEUE {
                key "name";
                leaf name {
                    type string;
                }
                leaf max-queue-len {
                    type uint64;
                }
                leaf avg-queue-len {
                    type uint64;
                }
                leaf transmit-pkts {
                    type uint64;
                }
                leaf transmit-octets {
                    type uint64;
                }
                leaf dropped-pkts {
                    type uint64;
                }
                leaf dropped-octets {
                    type uint64;
                }
                leaf ecn-marked-pkts {
                    type uint64;
                }
                leaf ecn-marked-octets {
                    type uint64;
                }
                leaf ecn-selected-pkts {
                    type uint64;
                }
                leaf ecn-selected-octets {
                    type uint64;
                }
            }
        }
        container INTERFACE_OUTPUT_CLASSIFIERS {
            list CLASSIFIER {
                key "name";
                leaf type {
                    type enumeration {
                        enum "NORMAL";
                        enum "STUB";
                        enum "NSSA";
                    }
                }
                leaf name {
                    type string;
                }
            }
        }
        container INTERFACE_OUTPUT_CLASSIFIER_TERMS {
            list TERM {
                key "id";
                leaf id {
                    type string;
                }
                leaf matched-packets {
                    type uint64;
                }
                leaf matched-octets {
                    type uint64;
                }
            }
        }
        container INTERFACE_OUTPUT_QUEUES {
            list QUEUE {
                key "name";
                leaf name {
                    type string;
                }
                leaf queue-management-profile {
                    type string;
                }
                leaf max-queue-len {
                    type uint64;
                }
                leaf avg-queue-len {
                    type uint64;
                }
                leaf transmit-pkts {
                    type uint64;
                }
                leaf transmit-octets {
                    type uint64;
                }
                leaf dropped-pkts {
                    type uint64;
                }
                leaf dropped-octets {
                    type uint64;
                }
                leaf ecn-marked-pkts {
                    type uint64;
                }
                leaf ecn-marked-octets {
                    type uint64;
                }
                leaf ecn-selected-pkts {
                    type uint64;
                }
                leaf ecn-selected-octets {
                    type uint64;
                }
            }
        }
        container INTERFACE_OUTPUT_SCHEDULER-POLICY_SCHEDULERS {
            list SCHEDULER {
                key "sequence";
                leaf sequence {
                    type string;
                }
                leaf conforming-pkts {
                    type uint64;
                }
                leaf conforming-octets {
                    type uint64;
                }
                leaf exceeding-pkts {
                    type uint64;
                }
                leaf exceeding-octets {
                    type uint64;
                }
                leaf violating-pkts {
                    type uint64;
                }
                leaf violating-octets {
                    type uint64;
                }
            }
        }
        container CLASSIFIERS {
            list CLASSIFIER {
                key "name";
                leaf name {
                    type string;
                }
                leaf type {
                    type enumeration {
                        enum "NORMAL";
                        enum "STUB";
                        enum "NSSA";
                    }
                }
            }
        }
        container CLASSIFIER_TERMS {
            list TERM {
                key "id";
                leaf id {
                    type string;
                }
                leaf source-mac {
                    type string;
                }
                leaf source-mac-mask {
                    type string;
                }
                leaf destination-mac {
                    type string;
                }
                leaf destination-mac-mask {
                    type string;
                }
                leaf ethertype {
                    type union {
                        type uint32 {
                            range "1536..65535";
                        }
                        type enumeration {
                            enum "ETHERTYPE_IPV4";
                            enum "ETHERTYPE_ARP";
                            enum "ETHERTYPE_VLAN";
                            enum "ETHERTYPE_IPV6";
                            enum "ETHERTYPE_MPLS";
                            enum "ETHERTYPE_LLDP";
                            enum "ETHERTYPE_ROCE";
                        }
                    }
                }
                leaf source-address {
                    type string;
                }
                leaf source-address-prefix-set {
                    type string;
                }
                leaf destination-address {
                    type string;
                }
                leaf destination-address-prefix-set {
                    type string;
                }
                leaf dscp {
                    type uint32 {
                        range "0..63";
                    }
                }
                leaf length {
                    type uint16;
                }
                leaf protocol {
                    type union {
                        type uint32 {
                            range "0..254";
                        }
                        type enumeration {
                            enum "IP_TCP";
                            enum "IP_UDP";
                            enum "IP_ICMP";
                            enum "IP_IGMP";
                            enum "IP_PIM";
                            enum "IP_RSVP";
                            enum "IP_GRE";
                            enum "IP_AUTH";
                            enum "IP_L2TP";
                            enum "IP_IN_IP";
                        }
                    }
                }
                leaf hop-limit {
                    type uint32 {
                        range "0..255";
                    }
                }
                leaf type {
                    type enumeration {
                        enum "";
                    }
                }
                leaf code {
                    type enumeration {
                        enum "NEIGHBOR_SOLICITATION_CODE";
                        enum "NEIGHBOR_ADVERTISEMENT_CODE";
                        enum "INVERSE_NEIGHBOR_ADVERTISEMENT_CODE";
                        enum "INVERSE_NEIGHBOR_SOLICITATION_CODE";
                    }
                }
                leaf source-flow-label {
                    type uint32 {
                        range "0..1048575";
                    }
                }
                leaf destination-flow-label {
                    type uint32 {
                        range "0..1048575";
                    }
                }
                leaf source-port {
                    type union {
                        type string;
                        type uint32 {
                        }
                        type enumeration {
                            enum "ANY";
                        }
                    }
                }
                leaf source-port-set {
                    type string;
                }
                leaf destination-port {
                    type union {
                        type string;
                        type uint32 {
                        }
                        type enumeration {
                            enum "ANY";
                        }
                    }
                }
                leaf destination-port-set {
                    type string;
                }
                leaf detail-mode {
                    type enumeration {
                        enum "EXPLICIT";
                        enum "BUILTIN";
                    }
                }
                leaf explicit-detail-match-mode {
                    type enumeration {
                        enum "ANY";
                        enum "ALL";
                    }
                }
                leaf builtin-detail {
                    type enumeration {
                        enum "TCP_INITIAL";
                        enum "TCP_ESTABLISHED";
                        enum "FRAGMENT";
                    }
                }
                leaf traffic-class {
                    type uint32 {
                        range "0..7";
                    }
                }
                leaf start-label-value {
                    type union {
                        type uint32 {
                            range "16..1048575";
                        }
                        type enumeration {
                            enum "IPV4_EXPLICIT_NULL";
                            enum "ROUTER_ALERT";
                            enum "IPV6_EXPLICIT_NULL";
                            enum "IMPLICIT_NULL";
                            enum "ENTROPY_LABEL_INDICATOR";
                            enum "NO_LABEL";
                        }
                    }
                }
                leaf end-label-value {
                    type union {
                        type uint32 {
                            range "16..1048575";
                        }
                        type enumeration {
                            enum "IPV4_EXPLICIT_NULL";
                            enum "ROUTER_ALERT";
                            enum "IPV6_EXPLICIT_NULL";
                            enum "IMPLICIT_NULL";
                            enum "ENTROPY_LABEL_INDICATOR";
                            enum "NO_LABEL";
                        }
                    }
                }
                leaf ttl-value {
                    type uint8;
                }
                leaf target-group {
                    type string;
                }
                leaf set-dscp {
                    type uint8;
                }
                leaf set-dot1p {
                    type uint8;
                }
                leaf set-mpls-tc {
                    type uint8;
                }
            }
        }
        container FORWARDING-GROUPS {
            list FORWARDING-GROUP {
                key "name";
                leaf name {
                    type string;
                }
                leaf fabric-priority {
                    type uint8;
                }
                leaf output-queue {
                    type string;
                }
                leaf unicast-output-queue {
                    type string;
                }
                leaf multicast-output-queue {
                    type string;
                }
            }
        }
        container QUEUES {
            list QUEUE {
                key "name";
                leaf name {
                    type string;
                }
                leaf queue-id {
                    type uint8;
                }
            }
        }
        container SCHEDULER-POLICIES {
            list SCHEDULER-POLICY {
                key "name";
                leaf name {
                    type string;
                }
            }
        }
        container SCHEDULER-POLICIES_SCHEDULER-POLICY_SCHEDULERS {
            list SCHEDULER {
                key "sequence";
                leaf sequence {
                    type string;
                }
                leaf type {
                    type enumeration {
                        enum "NORMAL";
                        enum "STUB";
                        enum "NSSA";
                    }
                }
                leaf priority {
                    type uint8;
                }
                leaf output-type {
                    type enumeration {
                        enum "SCHEDULER";
                        enum "FWD_GROUP";
                        enum "INTERFACE";
                    }
                }
                leaf child-scheduler {
                    type string;
                }
                leaf output-fwd-group {
                    type string;
                }
                leaf cir {
                    type uint64;
                }
                leaf cir-pct {
                    type uint32 {
                        range "0..100";
                    }
                }
                leaf cir-pct-remaining {
                    type uint32 {
                        range "0..100";
                    }
                }
                leaf bc {
                    type uint32;
                }
                leaf queuing-behavior {
                    type enumeration {
                        enum "SHAPE";
                        enum "POLICE";
                    }
                }
                leaf max-queue-depth-bytes {
                    type uint32;
                }
                leaf max-queue-depth-packets {
                    type uint32;
                }
                leaf max-queue-depth-percent {
                    type uint32 {
                        range "0..100";
                    }
                }
                leaf set-dscp {
                    type uint8;
                }
                leaf set-dot1p {
                    type uint8;
                }
                leaf set-mpls-tc {
                    type uint8;
                }
                leaf drop {
                    type boolean;
                }
                leaf pir {
                    type uint64;
                }
                leaf pir-pct {
                    type uint32 {
                        range "0..100";
                    }
                }
                leaf pir-pct-remaining {
                    type uint32 {
                        range "0..100";
                    }
                }
                leaf be {
                    type oc-yang:counter64;
                }
            }
        }
        container SCHEDULER-POLICIES_SCHEDULER-POLICY_SCHEDULER_INPUTS {
            list INPUT {
                key "id";
                leaf id {
                    type string;
                }
                leaf input-type {
                    type enumeration {
                        enum "QUEUE";
                        enum "IN_PROFILE";
                        enum "OUT_PROFILE";
                    }
                }
                leaf queue {
                    type string;
                }
                leaf weight {
                    type uint8;
                }
            }
        }
        container BUFFER-ALLOCATION-PROFILES {
            list BUFFER-ALLOCATION-PROFILE {
                key "name";
                leaf name {
                    type string;
                }
            }
        }
        container BUFFER-ALLOCATION-PROFILE_QUEUES {
            list QUEUE {
                key "name";
                leaf name {
                    type string;
                }
                leaf dedicated-buffer {
                    type uint64;
                }
                leaf dedicated-buffer-temporal {
                    type uint64;
                }
                leaf use-shared-buffer {
                    type boolean;
                }
                leaf shared-buffer-limit-type {
                    type enumeration {
                        enum "STATIC";
                        enum "DYNAMIC_BASED_ON_SCALING_FACTOR";
                    }
                }
                leaf static-shared-buffer-limit {
                    type uint32;
                }
                leaf static-shared-buffer-limit-temporal {
                    type uint32;
                }
                leaf dynamic-limit-scaling-factor {
                    type int32;
                }
            }
        }
        container QUEUE-MANAGEMENT-PROFILES {
            list QUEUE-MANAGEMENT-PROFILE {
                key "name";
                leaf name {
                    type string;
                }
                leaf min-threshold {
                    type uint64;
                }
                leaf max-threshold {
                    type uint64;
                }
                leaf min-threshold-percent {
                    type uint32 {
                        range "0..100";
                    }
                }
                leaf max-threshold-percent {
                    type uint32 {
                        range "0..100";
                    }
                }
                leaf enable-ecn {
                    type boolean;
                }
                leaf drop {
                    type boolean;
                }
                leaf weight {
                    type uint8;
                }
                leaf max-drop-probability-percent {
                    type uint32 {
                        range "0..100";
                    }
                }
            }
        }
    }

}
