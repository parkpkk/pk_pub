module sonic-openconfig-acl {
    namespace "http://github.com/sonic-net/openconfig/sonic-openconfig-acl";
    prefix sonic-openconfig-acl;
    yang-version 1.1;

    import ietf-inet-types {
        prefix inet;
    }

    organization
        "SONiC";

    contact
        "SONiC";

    description
        "SONIC OPENCONFIG YANG AUTO CONVERTION FOR OPENCONFIG-ACL";

    revision 2026-05-05 {
        description
            "Initial revision generated by YangIntegratedStandardizer.";
    }

    container sonic-openconfig-acl {
        container COMMON_SETTINGS {
            leaf counter-capability {
                type enumeration {
                    enum "INTERFACE_ONLY";
                    enum "AGGREGATE_ONLY";
                    enum "INTERFACE_AGGREGATE";
                }
            }
        }
        container ACL-SETS {
            list ACL-SET {
                key "name type";
                leaf name {
                    type string;
                }
                leaf type {
                    type enumeration {
                        enum "NORMAL";
                        enum "STUB";
                        enum "NSSA";
                    }
                }
                leaf description {
                    type string;
                }
            }
        }
        container ACL-SET_ACL-ENTRIES {
            list ACL-ENTRY {
                key "sequence-id";
                leaf sequence-id {
                    type string;
                }
                leaf description {
                    type string;
                }
                leaf matched-packets {
                    type uint64;
                }
                leaf matched-octets {
                    type uint64;
                }
                leaf source-mac {
                    type string;
                }
                leaf source-mac-mask {
                    type string;
                }
                leaf destination-mac {
                    type string;
                }
                leaf destination-mac-mask {
                    type string;
                }
                leaf ethertype {
                    type union {
                        type uint32 {
                            range "1536..65535";
                        }
                        type enumeration {
                            enum "ETHERTYPE_IPV4";
                            enum "ETHERTYPE_ARP";
                            enum "ETHERTYPE_VLAN";
                            enum "ETHERTYPE_IPV6";
                            enum "ETHERTYPE_MPLS";
                            enum "ETHERTYPE_LLDP";
                            enum "ETHERTYPE_ROCE";
                        }
                    }
                }
                leaf source-address {
                    type string;
                }
                leaf source-address-prefix-set {
                    type string;
                }
                leaf destination-address {
                    type string;
                }
                leaf destination-address-prefix-set {
                    type string;
                }
                leaf dscp {
                    type uint32 {
                        range "0..63";
                    }
                }
                leaf length {
                    type uint16;
                }
                leaf protocol {
                    type union {
                        type uint32 {
                            range "0..254";
                        }
                        type enumeration {
                            enum "IP_TCP";
                            enum "IP_UDP";
                            enum "IP_ICMP";
                            enum "IP_IGMP";
                            enum "IP_PIM";
                            enum "IP_RSVP";
                            enum "IP_GRE";
                            enum "IP_AUTH";
                            enum "IP_L2TP";
                            enum "IP_IN_IP";
                        }
                    }
                }
                leaf hop-limit {
                    type uint32 {
                        range "0..255";
                    }
                }
                leaf type {
                    type enumeration {
                        enum "";
                    }
                }
                leaf code {
                    type enumeration {
                        enum "NEIGHBOR_SOLICITATION_CODE";
                        enum "NEIGHBOR_ADVERTISEMENT_CODE";
                        enum "INVERSE_NEIGHBOR_ADVERTISEMENT_CODE";
                        enum "INVERSE_NEIGHBOR_SOLICITATION_CODE";
                    }
                }
                leaf traffic-class {
                    type uint32 {
                        range "0..7";
                    }
                }
                leaf start-label-value {
                    type union {
                        type uint32 {
                            range "16..1048575";
                        }
                        type enumeration {
                            enum "IPV4_EXPLICIT_NULL";
                            enum "ROUTER_ALERT";
                            enum "IPV6_EXPLICIT_NULL";
                            enum "IMPLICIT_NULL";
                            enum "ENTROPY_LABEL_INDICATOR";
                            enum "NO_LABEL";
                        }
                    }
                }
                leaf end-label-value {
                    type union {
                        type uint32 {
                            range "16..1048575";
                        }
                        type enumeration {
                            enum "IPV4_EXPLICIT_NULL";
                            enum "ROUTER_ALERT";
                            enum "IPV6_EXPLICIT_NULL";
                            enum "IMPLICIT_NULL";
                            enum "ENTROPY_LABEL_INDICATOR";
                            enum "NO_LABEL";
                        }
                    }
                }
                leaf ttl-value {
                    type uint8;
                }
                leaf source-flow-label {
                    type uint32 {
                        range "0..1048575";
                    }
                }
                leaf destination-flow-label {
                    type uint32 {
                        range "0..1048575";
                    }
                }
                leaf source-port {
                    type union {
                        type string;
                        type uint32 {
                        }
                        type enumeration {
                            enum "ANY";
                        }
                    }
                }
                leaf source-port-set {
                    type string;
                }
                leaf destination-port {
                    type union {
                        type string;
                        type uint32 {
                        }
                        type enumeration {
                            enum "ANY";
                        }
                    }
                }
                leaf destination-port-set {
                    type string;
                }
                leaf detail-mode {
                    type enumeration {
                        enum "EXPLICIT";
                        enum "BUILTIN";
                    }
                }
                leaf explicit-detail-match-mode {
                    type enumeration {
                        enum "ANY";
                        enum "ALL";
                    }
                }
                leaf builtin-detail {
                    type enumeration {
                        enum "TCP_INITIAL";
                        enum "TCP_ESTABLISHED";
                        enum "FRAGMENT";
                    }
                }
                leaf interface {
                    type string;
                }
                leaf subinterface {
                    type uint64;
                }
                leaf forwarding-action {
                    type enumeration {
                        enum "ACCEPT";
                        enum "DROP";
                        enum "REJECT";
                    }
                }
                leaf log-action {
                    type enumeration {
                        enum "LOG_SYSLOG";
                        enum "LOG_NONE";
                    }
                }
            }
        }
        container INTERFACES {
            list INTERFACE {
                key "id";
                leaf id {
                    type string;
                }
                leaf subinterface {
                    type uint64;
                }
            }
        }
        container INTERFACE_INGRESS-ACL-SETS {
            list INGRESS-ACL-SET {
                key "set-name type";
                leaf set-name {
                    type string;
                }
                leaf type {
                    type enumeration {
                        enum "NORMAL";
                        enum "STUB";
                        enum "NSSA";
                    }
                }
            }
        }
        container INTERFACE_INGRESS-ACL-SET_ACL-ENTRIES {
            list ACL-ENTRY {
                key "sequence-id";
                leaf sequence-id {
                    type string;
                }
                leaf matched-packets {
                    type uint64;
                }
                leaf matched-octets {
                    type uint64;
                }
            }
        }
        container INTERFACE_EGRESS-ACL-SETS {
            list EGRESS-ACL-SET {
                key "set-name type";
                leaf set-name {
                    type string;
                }
                leaf type {
                    type enumeration {
                        enum "NORMAL";
                        enum "STUB";
                        enum "NSSA";
                    }
                }
            }
        }
        container INTERFACE_EGRESS-ACL-SET_ACL-ENTRIES {
            list ACL-ENTRY {
                key "sequence-id";
                leaf sequence-id {
                    type string;
                }
                leaf matched-packets {
                    type uint64;
                }
                leaf matched-octets {
                    type uint64;
                }
            }
        }
    }

}
